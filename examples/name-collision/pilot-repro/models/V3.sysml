package V3 {
    private import ScalarValues::*;
    part def Vehicle {
        attribute mass : Real;
        attribute mass : Real;
    }
    part def Truck {
        attribute def load;
        attribute load : Real;
        attribute payload :> load;
    }
}
