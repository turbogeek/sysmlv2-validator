package VehicleTradeOffAnalysis{
    @Risk about engineTradeOffAnalysis::vehicle_b_engine4cyl::engine::fuelEfficiency {
        technicalRisk {
            probability = 0.3;
            impact = 0.5;
        }
    }
}
