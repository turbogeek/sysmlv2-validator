package PerfInheritance_200 {
    doc /* Generated performance-test model (PerfCorpusGenerator): an inheritance chain of 200 part definitions. */
    private import ScalarValues::*;

    part def Level_0000 {
        attribute value_0000 : Real default 0.0;
    }
    part def Level_0001 :> Level_0000 {
        attribute :>> value_0000 default 1.0;
        attribute value_0001 : Real default 0.0;
    }
    part def Level_0002 :> Level_0001 {
        attribute :>> value_0000 default 2.0;
        attribute value_0002 : Real default 0.0;
    }
    part def Level_0003 :> Level_0002 {
        attribute :>> value_0000 default 3.0;
        attribute value_0003 : Real default 0.0;
    }
    part def Level_0004 :> Level_0003 {
        attribute :>> value_0000 default 4.0;
        attribute value_0004 : Real default 0.0;
    }
    part def Level_0005 :> Level_0004 {
        attribute :>> value_0000 default 5.0;
        attribute value_0005 : Real default 0.0;
    }
    part def Level_0006 :> Level_0005 {
        attribute :>> value_0000 default 6.0;
        attribute value_0006 : Real default 0.0;
    }
    part def Level_0007 :> Level_0006 {
        attribute :>> value_0000 default 7.0;
        attribute value_0007 : Real default 0.0;
    }
    part def Level_0008 :> Level_0007 {
        attribute :>> value_0000 default 8.0;
        attribute value_0008 : Real default 0.0;
    }
    part def Level_0009 :> Level_0008 {
        attribute :>> value_0000 default 9.0;
        attribute value_0009 : Real default 0.0;
    }
    part def Level_0010 :> Level_0009 {
        attribute :>> value_0000 default 10.0;
        attribute value_0010 : Real default 0.0;
    }
    part def Level_0011 :> Level_0010 {
        attribute :>> value_0000 default 11.0;
        attribute value_0011 : Real default 0.0;
    }
    part def Level_0012 :> Level_0011 {
        attribute :>> value_0000 default 12.0;
        attribute value_0012 : Real default 0.0;
    }
    part def Level_0013 :> Level_0012 {
        attribute :>> value_0000 default 13.0;
        attribute value_0013 : Real default 0.0;
    }
    part def Level_0014 :> Level_0013 {
        attribute :>> value_0000 default 14.0;
        attribute value_0014 : Real default 0.0;
    }
    part def Level_0015 :> Level_0014 {
        attribute :>> value_0000 default 15.0;
        attribute value_0015 : Real default 0.0;
    }
    part def Level_0016 :> Level_0015 {
        attribute :>> value_0000 default 16.0;
        attribute value_0016 : Real default 0.0;
    }
    part def Level_0017 :> Level_0016 {
        attribute :>> value_0000 default 17.0;
        attribute value_0017 : Real default 0.0;
    }
    part def Level_0018 :> Level_0017 {
        attribute :>> value_0000 default 18.0;
        attribute value_0018 : Real default 0.0;
    }
    part def Level_0019 :> Level_0018 {
        attribute :>> value_0000 default 19.0;
        attribute value_0019 : Real default 0.0;
    }
    part def Level_0020 :> Level_0019 {
        attribute :>> value_0000 default 20.0;
        attribute value_0020 : Real default 0.0;
    }
    part def Level_0021 :> Level_0020 {
        attribute :>> value_0000 default 21.0;
        attribute value_0021 : Real default 0.0;
    }
    part def Level_0022 :> Level_0021 {
        attribute :>> value_0000 default 22.0;
        attribute value_0022 : Real default 0.0;
    }
    part def Level_0023 :> Level_0022 {
        attribute :>> value_0000 default 23.0;
        attribute value_0023 : Real default 0.0;
    }
    part def Level_0024 :> Level_0023 {
        attribute :>> value_0000 default 24.0;
        attribute value_0024 : Real default 0.0;
    }
    part def Level_0025 :> Level_0024 {
        attribute :>> value_0000 default 25.0;
        attribute value_0025 : Real default 0.0;
    }
    part def Level_0026 :> Level_0025 {
        attribute :>> value_0000 default 26.0;
        attribute value_0026 : Real default 0.0;
    }
    part def Level_0027 :> Level_0026 {
        attribute :>> value_0000 default 27.0;
        attribute value_0027 : Real default 0.0;
    }
    part def Level_0028 :> Level_0027 {
        attribute :>> value_0000 default 28.0;
        attribute value_0028 : Real default 0.0;
    }
    part def Level_0029 :> Level_0028 {
        attribute :>> value_0000 default 29.0;
        attribute value_0029 : Real default 0.0;
    }
    part def Level_0030 :> Level_0029 {
        attribute :>> value_0000 default 30.0;
        attribute value_0030 : Real default 0.0;
    }
    part def Level_0031 :> Level_0030 {
        attribute :>> value_0000 default 31.0;
        attribute value_0031 : Real default 0.0;
    }
    part def Level_0032 :> Level_0031 {
        attribute :>> value_0000 default 32.0;
        attribute value_0032 : Real default 0.0;
    }
    part def Level_0033 :> Level_0032 {
        attribute :>> value_0000 default 33.0;
        attribute value_0033 : Real default 0.0;
    }
    part def Level_0034 :> Level_0033 {
        attribute :>> value_0000 default 34.0;
        attribute value_0034 : Real default 0.0;
    }
    part def Level_0035 :> Level_0034 {
        attribute :>> value_0000 default 35.0;
        attribute value_0035 : Real default 0.0;
    }
    part def Level_0036 :> Level_0035 {
        attribute :>> value_0000 default 36.0;
        attribute value_0036 : Real default 0.0;
    }
    part def Level_0037 :> Level_0036 {
        attribute :>> value_0000 default 37.0;
        attribute value_0037 : Real default 0.0;
    }
    part def Level_0038 :> Level_0037 {
        attribute :>> value_0000 default 38.0;
        attribute value_0038 : Real default 0.0;
    }
    part def Level_0039 :> Level_0038 {
        attribute :>> value_0000 default 39.0;
        attribute value_0039 : Real default 0.0;
    }
    part def Level_0040 :> Level_0039 {
        attribute :>> value_0000 default 40.0;
        attribute value_0040 : Real default 0.0;
    }
    part def Level_0041 :> Level_0040 {
        attribute :>> value_0000 default 41.0;
        attribute value_0041 : Real default 0.0;
    }
    part def Level_0042 :> Level_0041 {
        attribute :>> value_0000 default 42.0;
        attribute value_0042 : Real default 0.0;
    }
    part def Level_0043 :> Level_0042 {
        attribute :>> value_0000 default 43.0;
        attribute value_0043 : Real default 0.0;
    }
    part def Level_0044 :> Level_0043 {
        attribute :>> value_0000 default 44.0;
        attribute value_0044 : Real default 0.0;
    }
    part def Level_0045 :> Level_0044 {
        attribute :>> value_0000 default 45.0;
        attribute value_0045 : Real default 0.0;
    }
    part def Level_0046 :> Level_0045 {
        attribute :>> value_0000 default 46.0;
        attribute value_0046 : Real default 0.0;
    }
    part def Level_0047 :> Level_0046 {
        attribute :>> value_0000 default 47.0;
        attribute value_0047 : Real default 0.0;
    }
    part def Level_0048 :> Level_0047 {
        attribute :>> value_0000 default 48.0;
        attribute value_0048 : Real default 0.0;
    }
    part def Level_0049 :> Level_0048 {
        attribute :>> value_0000 default 49.0;
        attribute value_0049 : Real default 0.0;
    }
    part def Level_0050 :> Level_0049 {
        attribute :>> value_0000 default 50.0;
        attribute value_0050 : Real default 0.0;
    }
    part def Level_0051 :> Level_0050 {
        attribute :>> value_0000 default 51.0;
        attribute value_0051 : Real default 0.0;
    }
    part def Level_0052 :> Level_0051 {
        attribute :>> value_0000 default 52.0;
        attribute value_0052 : Real default 0.0;
    }
    part def Level_0053 :> Level_0052 {
        attribute :>> value_0000 default 53.0;
        attribute value_0053 : Real default 0.0;
    }
    part def Level_0054 :> Level_0053 {
        attribute :>> value_0000 default 54.0;
        attribute value_0054 : Real default 0.0;
    }
    part def Level_0055 :> Level_0054 {
        attribute :>> value_0000 default 55.0;
        attribute value_0055 : Real default 0.0;
    }
    part def Level_0056 :> Level_0055 {
        attribute :>> value_0000 default 56.0;
        attribute value_0056 : Real default 0.0;
    }
    part def Level_0057 :> Level_0056 {
        attribute :>> value_0000 default 57.0;
        attribute value_0057 : Real default 0.0;
    }
    part def Level_0058 :> Level_0057 {
        attribute :>> value_0000 default 58.0;
        attribute value_0058 : Real default 0.0;
    }
    part def Level_0059 :> Level_0058 {
        attribute :>> value_0000 default 59.0;
        attribute value_0059 : Real default 0.0;
    }
    part def Level_0060 :> Level_0059 {
        attribute :>> value_0000 default 60.0;
        attribute value_0060 : Real default 0.0;
    }
    part def Level_0061 :> Level_0060 {
        attribute :>> value_0000 default 61.0;
        attribute value_0061 : Real default 0.0;
    }
    part def Level_0062 :> Level_0061 {
        attribute :>> value_0000 default 62.0;
        attribute value_0062 : Real default 0.0;
    }
    part def Level_0063 :> Level_0062 {
        attribute :>> value_0000 default 63.0;
        attribute value_0063 : Real default 0.0;
    }
    part def Level_0064 :> Level_0063 {
        attribute :>> value_0000 default 64.0;
        attribute value_0064 : Real default 0.0;
    }
    part def Level_0065 :> Level_0064 {
        attribute :>> value_0000 default 65.0;
        attribute value_0065 : Real default 0.0;
    }
    part def Level_0066 :> Level_0065 {
        attribute :>> value_0000 default 66.0;
        attribute value_0066 : Real default 0.0;
    }
    part def Level_0067 :> Level_0066 {
        attribute :>> value_0000 default 67.0;
        attribute value_0067 : Real default 0.0;
    }
    part def Level_0068 :> Level_0067 {
        attribute :>> value_0000 default 68.0;
        attribute value_0068 : Real default 0.0;
    }
    part def Level_0069 :> Level_0068 {
        attribute :>> value_0000 default 69.0;
        attribute value_0069 : Real default 0.0;
    }
    part def Level_0070 :> Level_0069 {
        attribute :>> value_0000 default 70.0;
        attribute value_0070 : Real default 0.0;
    }
    part def Level_0071 :> Level_0070 {
        attribute :>> value_0000 default 71.0;
        attribute value_0071 : Real default 0.0;
    }
    part def Level_0072 :> Level_0071 {
        attribute :>> value_0000 default 72.0;
        attribute value_0072 : Real default 0.0;
    }
    part def Level_0073 :> Level_0072 {
        attribute :>> value_0000 default 73.0;
        attribute value_0073 : Real default 0.0;
    }
    part def Level_0074 :> Level_0073 {
        attribute :>> value_0000 default 74.0;
        attribute value_0074 : Real default 0.0;
    }
    part def Level_0075 :> Level_0074 {
        attribute :>> value_0000 default 75.0;
        attribute value_0075 : Real default 0.0;
    }
    part def Level_0076 :> Level_0075 {
        attribute :>> value_0000 default 76.0;
        attribute value_0076 : Real default 0.0;
    }
    part def Level_0077 :> Level_0076 {
        attribute :>> value_0000 default 77.0;
        attribute value_0077 : Real default 0.0;
    }
    part def Level_0078 :> Level_0077 {
        attribute :>> value_0000 default 78.0;
        attribute value_0078 : Real default 0.0;
    }
    part def Level_0079 :> Level_0078 {
        attribute :>> value_0000 default 79.0;
        attribute value_0079 : Real default 0.0;
    }
    part def Level_0080 :> Level_0079 {
        attribute :>> value_0000 default 80.0;
        attribute value_0080 : Real default 0.0;
    }
    part def Level_0081 :> Level_0080 {
        attribute :>> value_0000 default 81.0;
        attribute value_0081 : Real default 0.0;
    }
    part def Level_0082 :> Level_0081 {
        attribute :>> value_0000 default 82.0;
        attribute value_0082 : Real default 0.0;
    }
    part def Level_0083 :> Level_0082 {
        attribute :>> value_0000 default 83.0;
        attribute value_0083 : Real default 0.0;
    }
    part def Level_0084 :> Level_0083 {
        attribute :>> value_0000 default 84.0;
        attribute value_0084 : Real default 0.0;
    }
    part def Level_0085 :> Level_0084 {
        attribute :>> value_0000 default 85.0;
        attribute value_0085 : Real default 0.0;
    }
    part def Level_0086 :> Level_0085 {
        attribute :>> value_0000 default 86.0;
        attribute value_0086 : Real default 0.0;
    }
    part def Level_0087 :> Level_0086 {
        attribute :>> value_0000 default 87.0;
        attribute value_0087 : Real default 0.0;
    }
    part def Level_0088 :> Level_0087 {
        attribute :>> value_0000 default 88.0;
        attribute value_0088 : Real default 0.0;
    }
    part def Level_0089 :> Level_0088 {
        attribute :>> value_0000 default 89.0;
        attribute value_0089 : Real default 0.0;
    }
    part def Level_0090 :> Level_0089 {
        attribute :>> value_0000 default 90.0;
        attribute value_0090 : Real default 0.0;
    }
    part def Level_0091 :> Level_0090 {
        attribute :>> value_0000 default 91.0;
        attribute value_0091 : Real default 0.0;
    }
    part def Level_0092 :> Level_0091 {
        attribute :>> value_0000 default 92.0;
        attribute value_0092 : Real default 0.0;
    }
    part def Level_0093 :> Level_0092 {
        attribute :>> value_0000 default 93.0;
        attribute value_0093 : Real default 0.0;
    }
    part def Level_0094 :> Level_0093 {
        attribute :>> value_0000 default 94.0;
        attribute value_0094 : Real default 0.0;
    }
    part def Level_0095 :> Level_0094 {
        attribute :>> value_0000 default 95.0;
        attribute value_0095 : Real default 0.0;
    }
    part def Level_0096 :> Level_0095 {
        attribute :>> value_0000 default 96.0;
        attribute value_0096 : Real default 0.0;
    }
    part def Level_0097 :> Level_0096 {
        attribute :>> value_0000 default 97.0;
        attribute value_0097 : Real default 0.0;
    }
    part def Level_0098 :> Level_0097 {
        attribute :>> value_0000 default 98.0;
        attribute value_0098 : Real default 0.0;
    }
    part def Level_0099 :> Level_0098 {
        attribute :>> value_0000 default 99.0;
        attribute value_0099 : Real default 0.0;
    }
    part def Level_0100 :> Level_0099 {
        attribute :>> value_0000 default 100.0;
        attribute value_0100 : Real default 0.0;
    }
    part def Level_0101 :> Level_0100 {
        attribute :>> value_0000 default 101.0;
        attribute value_0101 : Real default 0.0;
    }
    part def Level_0102 :> Level_0101 {
        attribute :>> value_0000 default 102.0;
        attribute value_0102 : Real default 0.0;
    }
    part def Level_0103 :> Level_0102 {
        attribute :>> value_0000 default 103.0;
        attribute value_0103 : Real default 0.0;
    }
    part def Level_0104 :> Level_0103 {
        attribute :>> value_0000 default 104.0;
        attribute value_0104 : Real default 0.0;
    }
    part def Level_0105 :> Level_0104 {
        attribute :>> value_0000 default 105.0;
        attribute value_0105 : Real default 0.0;
    }
    part def Level_0106 :> Level_0105 {
        attribute :>> value_0000 default 106.0;
        attribute value_0106 : Real default 0.0;
    }
    part def Level_0107 :> Level_0106 {
        attribute :>> value_0000 default 107.0;
        attribute value_0107 : Real default 0.0;
    }
    part def Level_0108 :> Level_0107 {
        attribute :>> value_0000 default 108.0;
        attribute value_0108 : Real default 0.0;
    }
    part def Level_0109 :> Level_0108 {
        attribute :>> value_0000 default 109.0;
        attribute value_0109 : Real default 0.0;
    }
    part def Level_0110 :> Level_0109 {
        attribute :>> value_0000 default 110.0;
        attribute value_0110 : Real default 0.0;
    }
    part def Level_0111 :> Level_0110 {
        attribute :>> value_0000 default 111.0;
        attribute value_0111 : Real default 0.0;
    }
    part def Level_0112 :> Level_0111 {
        attribute :>> value_0000 default 112.0;
        attribute value_0112 : Real default 0.0;
    }
    part def Level_0113 :> Level_0112 {
        attribute :>> value_0000 default 113.0;
        attribute value_0113 : Real default 0.0;
    }
    part def Level_0114 :> Level_0113 {
        attribute :>> value_0000 default 114.0;
        attribute value_0114 : Real default 0.0;
    }
    part def Level_0115 :> Level_0114 {
        attribute :>> value_0000 default 115.0;
        attribute value_0115 : Real default 0.0;
    }
    part def Level_0116 :> Level_0115 {
        attribute :>> value_0000 default 116.0;
        attribute value_0116 : Real default 0.0;
    }
    part def Level_0117 :> Level_0116 {
        attribute :>> value_0000 default 117.0;
        attribute value_0117 : Real default 0.0;
    }
    part def Level_0118 :> Level_0117 {
        attribute :>> value_0000 default 118.0;
        attribute value_0118 : Real default 0.0;
    }
    part def Level_0119 :> Level_0118 {
        attribute :>> value_0000 default 119.0;
        attribute value_0119 : Real default 0.0;
    }
    part def Level_0120 :> Level_0119 {
        attribute :>> value_0000 default 120.0;
        attribute value_0120 : Real default 0.0;
    }
    part def Level_0121 :> Level_0120 {
        attribute :>> value_0000 default 121.0;
        attribute value_0121 : Real default 0.0;
    }
    part def Level_0122 :> Level_0121 {
        attribute :>> value_0000 default 122.0;
        attribute value_0122 : Real default 0.0;
    }
    part def Level_0123 :> Level_0122 {
        attribute :>> value_0000 default 123.0;
        attribute value_0123 : Real default 0.0;
    }
    part def Level_0124 :> Level_0123 {
        attribute :>> value_0000 default 124.0;
        attribute value_0124 : Real default 0.0;
    }
    part def Level_0125 :> Level_0124 {
        attribute :>> value_0000 default 125.0;
        attribute value_0125 : Real default 0.0;
    }
    part def Level_0126 :> Level_0125 {
        attribute :>> value_0000 default 126.0;
        attribute value_0126 : Real default 0.0;
    }
    part def Level_0127 :> Level_0126 {
        attribute :>> value_0000 default 127.0;
        attribute value_0127 : Real default 0.0;
    }
    part def Level_0128 :> Level_0127 {
        attribute :>> value_0000 default 128.0;
        attribute value_0128 : Real default 0.0;
    }
    part def Level_0129 :> Level_0128 {
        attribute :>> value_0000 default 129.0;
        attribute value_0129 : Real default 0.0;
    }
    part def Level_0130 :> Level_0129 {
        attribute :>> value_0000 default 130.0;
        attribute value_0130 : Real default 0.0;
    }
    part def Level_0131 :> Level_0130 {
        attribute :>> value_0000 default 131.0;
        attribute value_0131 : Real default 0.0;
    }
    part def Level_0132 :> Level_0131 {
        attribute :>> value_0000 default 132.0;
        attribute value_0132 : Real default 0.0;
    }
    part def Level_0133 :> Level_0132 {
        attribute :>> value_0000 default 133.0;
        attribute value_0133 : Real default 0.0;
    }
    part def Level_0134 :> Level_0133 {
        attribute :>> value_0000 default 134.0;
        attribute value_0134 : Real default 0.0;
    }
    part def Level_0135 :> Level_0134 {
        attribute :>> value_0000 default 135.0;
        attribute value_0135 : Real default 0.0;
    }
    part def Level_0136 :> Level_0135 {
        attribute :>> value_0000 default 136.0;
        attribute value_0136 : Real default 0.0;
    }
    part def Level_0137 :> Level_0136 {
        attribute :>> value_0000 default 137.0;
        attribute value_0137 : Real default 0.0;
    }
    part def Level_0138 :> Level_0137 {
        attribute :>> value_0000 default 138.0;
        attribute value_0138 : Real default 0.0;
    }
    part def Level_0139 :> Level_0138 {
        attribute :>> value_0000 default 139.0;
        attribute value_0139 : Real default 0.0;
    }
    part def Level_0140 :> Level_0139 {
        attribute :>> value_0000 default 140.0;
        attribute value_0140 : Real default 0.0;
    }
    part def Level_0141 :> Level_0140 {
        attribute :>> value_0000 default 141.0;
        attribute value_0141 : Real default 0.0;
    }
    part def Level_0142 :> Level_0141 {
        attribute :>> value_0000 default 142.0;
        attribute value_0142 : Real default 0.0;
    }
    part def Level_0143 :> Level_0142 {
        attribute :>> value_0000 default 143.0;
        attribute value_0143 : Real default 0.0;
    }
    part def Level_0144 :> Level_0143 {
        attribute :>> value_0000 default 144.0;
        attribute value_0144 : Real default 0.0;
    }
    part def Level_0145 :> Level_0144 {
        attribute :>> value_0000 default 145.0;
        attribute value_0145 : Real default 0.0;
    }
    part def Level_0146 :> Level_0145 {
        attribute :>> value_0000 default 146.0;
        attribute value_0146 : Real default 0.0;
    }
    part def Level_0147 :> Level_0146 {
        attribute :>> value_0000 default 147.0;
        attribute value_0147 : Real default 0.0;
    }
    part def Level_0148 :> Level_0147 {
        attribute :>> value_0000 default 148.0;
        attribute value_0148 : Real default 0.0;
    }
    part def Level_0149 :> Level_0148 {
        attribute :>> value_0000 default 149.0;
        attribute value_0149 : Real default 0.0;
    }
    part def Level_0150 :> Level_0149 {
        attribute :>> value_0000 default 150.0;
        attribute value_0150 : Real default 0.0;
    }
    part def Level_0151 :> Level_0150 {
        attribute :>> value_0000 default 151.0;
        attribute value_0151 : Real default 0.0;
    }
    part def Level_0152 :> Level_0151 {
        attribute :>> value_0000 default 152.0;
        attribute value_0152 : Real default 0.0;
    }
    part def Level_0153 :> Level_0152 {
        attribute :>> value_0000 default 153.0;
        attribute value_0153 : Real default 0.0;
    }
    part def Level_0154 :> Level_0153 {
        attribute :>> value_0000 default 154.0;
        attribute value_0154 : Real default 0.0;
    }
    part def Level_0155 :> Level_0154 {
        attribute :>> value_0000 default 155.0;
        attribute value_0155 : Real default 0.0;
    }
    part def Level_0156 :> Level_0155 {
        attribute :>> value_0000 default 156.0;
        attribute value_0156 : Real default 0.0;
    }
    part def Level_0157 :> Level_0156 {
        attribute :>> value_0000 default 157.0;
        attribute value_0157 : Real default 0.0;
    }
    part def Level_0158 :> Level_0157 {
        attribute :>> value_0000 default 158.0;
        attribute value_0158 : Real default 0.0;
    }
    part def Level_0159 :> Level_0158 {
        attribute :>> value_0000 default 159.0;
        attribute value_0159 : Real default 0.0;
    }
    part def Level_0160 :> Level_0159 {
        attribute :>> value_0000 default 160.0;
        attribute value_0160 : Real default 0.0;
    }
    part def Level_0161 :> Level_0160 {
        attribute :>> value_0000 default 161.0;
        attribute value_0161 : Real default 0.0;
    }
    part def Level_0162 :> Level_0161 {
        attribute :>> value_0000 default 162.0;
        attribute value_0162 : Real default 0.0;
    }
    part def Level_0163 :> Level_0162 {
        attribute :>> value_0000 default 163.0;
        attribute value_0163 : Real default 0.0;
    }
    part def Level_0164 :> Level_0163 {
        attribute :>> value_0000 default 164.0;
        attribute value_0164 : Real default 0.0;
    }
    part def Level_0165 :> Level_0164 {
        attribute :>> value_0000 default 165.0;
        attribute value_0165 : Real default 0.0;
    }
    part def Level_0166 :> Level_0165 {
        attribute :>> value_0000 default 166.0;
        attribute value_0166 : Real default 0.0;
    }
    part def Level_0167 :> Level_0166 {
        attribute :>> value_0000 default 167.0;
        attribute value_0167 : Real default 0.0;
    }
    part def Level_0168 :> Level_0167 {
        attribute :>> value_0000 default 168.0;
        attribute value_0168 : Real default 0.0;
    }
    part def Level_0169 :> Level_0168 {
        attribute :>> value_0000 default 169.0;
        attribute value_0169 : Real default 0.0;
    }
    part def Level_0170 :> Level_0169 {
        attribute :>> value_0000 default 170.0;
        attribute value_0170 : Real default 0.0;
    }
    part def Level_0171 :> Level_0170 {
        attribute :>> value_0000 default 171.0;
        attribute value_0171 : Real default 0.0;
    }
    part def Level_0172 :> Level_0171 {
        attribute :>> value_0000 default 172.0;
        attribute value_0172 : Real default 0.0;
    }
    part def Level_0173 :> Level_0172 {
        attribute :>> value_0000 default 173.0;
        attribute value_0173 : Real default 0.0;
    }
    part def Level_0174 :> Level_0173 {
        attribute :>> value_0000 default 174.0;
        attribute value_0174 : Real default 0.0;
    }
    part def Level_0175 :> Level_0174 {
        attribute :>> value_0000 default 175.0;
        attribute value_0175 : Real default 0.0;
    }
    part def Level_0176 :> Level_0175 {
        attribute :>> value_0000 default 176.0;
        attribute value_0176 : Real default 0.0;
    }
    part def Level_0177 :> Level_0176 {
        attribute :>> value_0000 default 177.0;
        attribute value_0177 : Real default 0.0;
    }
    part def Level_0178 :> Level_0177 {
        attribute :>> value_0000 default 178.0;
        attribute value_0178 : Real default 0.0;
    }
    part def Level_0179 :> Level_0178 {
        attribute :>> value_0000 default 179.0;
        attribute value_0179 : Real default 0.0;
    }
    part def Level_0180 :> Level_0179 {
        attribute :>> value_0000 default 180.0;
        attribute value_0180 : Real default 0.0;
    }
    part def Level_0181 :> Level_0180 {
        attribute :>> value_0000 default 181.0;
        attribute value_0181 : Real default 0.0;
    }
    part def Level_0182 :> Level_0181 {
        attribute :>> value_0000 default 182.0;
        attribute value_0182 : Real default 0.0;
    }
    part def Level_0183 :> Level_0182 {
        attribute :>> value_0000 default 183.0;
        attribute value_0183 : Real default 0.0;
    }
    part def Level_0184 :> Level_0183 {
        attribute :>> value_0000 default 184.0;
        attribute value_0184 : Real default 0.0;
    }
    part def Level_0185 :> Level_0184 {
        attribute :>> value_0000 default 185.0;
        attribute value_0185 : Real default 0.0;
    }
    part def Level_0186 :> Level_0185 {
        attribute :>> value_0000 default 186.0;
        attribute value_0186 : Real default 0.0;
    }
    part def Level_0187 :> Level_0186 {
        attribute :>> value_0000 default 187.0;
        attribute value_0187 : Real default 0.0;
    }
    part def Level_0188 :> Level_0187 {
        attribute :>> value_0000 default 188.0;
        attribute value_0188 : Real default 0.0;
    }
    part def Level_0189 :> Level_0188 {
        attribute :>> value_0000 default 189.0;
        attribute value_0189 : Real default 0.0;
    }
    part def Level_0190 :> Level_0189 {
        attribute :>> value_0000 default 190.0;
        attribute value_0190 : Real default 0.0;
    }
    part def Level_0191 :> Level_0190 {
        attribute :>> value_0000 default 191.0;
        attribute value_0191 : Real default 0.0;
    }
    part def Level_0192 :> Level_0191 {
        attribute :>> value_0000 default 192.0;
        attribute value_0192 : Real default 0.0;
    }
    part def Level_0193 :> Level_0192 {
        attribute :>> value_0000 default 193.0;
        attribute value_0193 : Real default 0.0;
    }
    part def Level_0194 :> Level_0193 {
        attribute :>> value_0000 default 194.0;
        attribute value_0194 : Real default 0.0;
    }
    part def Level_0195 :> Level_0194 {
        attribute :>> value_0000 default 195.0;
        attribute value_0195 : Real default 0.0;
    }
    part def Level_0196 :> Level_0195 {
        attribute :>> value_0000 default 196.0;
        attribute value_0196 : Real default 0.0;
    }
    part def Level_0197 :> Level_0196 {
        attribute :>> value_0000 default 197.0;
        attribute value_0197 : Real default 0.0;
    }
    part def Level_0198 :> Level_0197 {
        attribute :>> value_0000 default 198.0;
        attribute value_0198 : Real default 0.0;
    }
    part def Level_0199 :> Level_0198 {
        attribute :>> value_0000 default 199.0;
        attribute value_0199 : Real default 0.0;
    }

    part deepest : Level_0199 {
        attribute :>> value_0000 = 42.0;
        attribute :>> value_0198 = 7.0;
    }
}
