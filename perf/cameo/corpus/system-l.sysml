package PerfSystem_l {
    doc /* Generated performance-test model (PerfCorpusGenerator): 1000 subsystems. */
    private import ScalarValues::*;
    private import ISQ::*;
    private import SI::*;

    package Common {
        enum def Health { enum ok; enum degraded; enum failed; }
        item def Packet {
            attribute size : Integer;
            attribute priority : Integer default 0;
        }
        port def PowerPort {
            out attribute supplyVoltage : Real;
        }
        port def DataPort {
            in item packet : Packet;
        }
        interface def PowerLink {
            end source : PowerPort;
            end sink : ~PowerPort;
        }
        abstract part def Component {
            attribute mass :> ISQ::mass;
            attribute cost : Real;
            attribute health : Health default Health::ok;
            port power : ~PowerPort;
        }
        action def Process {
            in input : Packet;
            out output : Packet;
        }
        calc def TotalMass {
            in masses : MassValue[0..*];
            return total : MassValue = NumericalFunctions::sum(masses);
        }
        requirement def MassLimit {
            subject component : Component;
            attribute limit : MassValue;
            require constraint { component.mass <= limit }
        }
        state def Lifecycle {
            entry; then off;
            state off;
            state on;
            transition powerOn first off then on;
            transition powerOff first on then off;
        }
    }

    package Subsystem_0001 {
        part def Sensor_0001 :> Common::Component {
            attribute :>> mass = 0.21 [kg];
            attribute :>> cost = 31.0;
            attribute range : Real = 101.0;
            port data : Common::DataPort;
        }
        part def Controller_0001 :> Common::Component {
            attribute :>> mass = 1.10 [kg];
            attribute :>> cost = 201.0;
            port supply : Common::PowerPort;
            part sensors : Sensor_0001[2];
            action smooth : Common::Process;
            action forward : Common::Process;
            succession first smooth then forward;
            exhibit state lifecycle : Common::Lifecycle;
        }
        requirement controllerMass_0001 : Common::MassLimit {
            subject component : Controller_0001;
            attribute :>> limit = 2.0 [kg];
        }
    }

    package Subsystem_0002 {
        part def Sensor_0002 :> Common::Component {
            attribute :>> mass = 0.22 [kg];
            attribute :>> cost = 32.0;
            attribute range : Real = 102.0;
            port data : Common::DataPort;
        }
        part def Controller_0002 :> Common::Component {
            attribute :>> mass = 1.20 [kg];
            attribute :>> cost = 202.0;
            port supply : Common::PowerPort;
            part sensors : Sensor_0002[2];
            action smooth : Common::Process;
            action forward : Common::Process;
            succession first smooth then forward;
            exhibit state lifecycle : Common::Lifecycle;
        }
        requirement controllerMass_0002 : Common::MassLimit {
            subject component : Controller_0002;
            attribute :>> limit = 2.0 [kg];
        }
    }

    package Subsystem_0003 {
        part def Sensor_0003 :> Common::Component {
            attribute :>> mass = 0.23 [kg];
            attribute :>> cost = 33.0;
            attribute range : Real = 103.0;
            port data : Common::DataPort;
        }
        part def Controller_0003 :> Common::Component {
            attribute :>> mass = 1.30 [kg];
            attribute :>> cost = 203.0;
            port supply : Common::PowerPort;
            part sensors : Sensor_0003[2];
            action smooth : Common::Process;
            action forward : Common::Process;
            succession first smooth then forward;
            exhibit state lifecycle : Common::Lifecycle;
        }
        requirement controllerMass_0003 : Common::MassLimit {
            subject component : Controller_0003;
            attribute :>> limit = 2.0 [kg];
        }
    }

    package Subsystem_0004 {
        part def Sensor_0004 :> Common::Component {
            attribute :>> mass = 0.24 [kg];
            attribute :>> cost = 34.0;
            attribute range : Real = 104.0;
            port data : Common::DataPort;
        }
        part def Controller_0004 :> Common::Component {
            attribute :>> mass = 1.40 [kg];
            attribute :>> cost = 204.0;
            port supply : Common::PowerPort;
            part sensors : Sensor_0004[2];
            action smooth : Common::Process;
            action forward : Common::Process;
            succession first smooth then forward;
            exhibit state lifecycle : Common::Lifecycle;
        }
        requirement controllerMass_0004 : Common::MassLimit {
            subject component : Controller_0004;
            attribute :>> limit = 2.0 [kg];
        }
    }

    package Subsystem_0005 {
        part def Sensor_0005 :> Common::Component {
            attribute :>> mass = 0.20 [kg];
            attribute :>> cost = 35.0;
            attribute range : Real = 105.0;
            port data : Common::DataPort;
        }
        part def Controller_0005 :> Common::Component {
            attribute :>> mass = 1.50 [kg];
            attribute :>> cost = 205.0;
            port supply : Common::PowerPort;
            part sensors : Sensor_0005[2];
            action smooth : Common::Process;
            action forward : Common::Process;
            succession first smooth then forward;
            exhibit state lifecycle : Common::Lifecycle;
        }
        requirement controllerMass_0005 : Common::MassLimit {
            subject component : Controller_0005;
            attribute :>> limit = 2.0 [kg];
        }
    }

    package Subsystem_0006 {
        part def Sensor_0006 :> Common::Component {
            attribute :>> mass = 0.21 [kg];
            attribute :>> cost = 36.0;
            attribute range : Real = 106.0;
            port data : Common::DataPort;
        }
        part def Controller_0006 :> Common::Component {
            attribute :>> mass = 1.60 [kg];
            attribute :>> cost = 206.0;
            port supply : Common::PowerPort;
            part sensors : Sensor_0006[2];
            action smooth : Common::Process;
            action forward : Common::Process;
            succession first smooth then forward;
            exhibit state lifecycle : Common::Lifecycle;
        }
        requirement controllerMass_0006 : Common::MassLimit {
            subject component : Controller_0006;
            attribute :>> limit = 2.0 [kg];
        }
    }

    package Subsystem_0007 {
        part def Sensor_0007 :> Common::Component {
            attribute :>> mass = 0.22 [kg];
            attribute :>> cost = 37.0;
            attribute range : Real = 107.0;
            port data : Common::DataPort;
        }
        part def Controller_0007 :> Common::Component {
            attribute :>> mass = 1.00 [kg];
            attribute :>> cost = 207.0;
            port supply : Common::PowerPort;
            part sensors : Sensor_0007[2];
            action smooth : Common::Process;
            action forward : Common::Process;
            succession first smooth then forward;
            exhibit state lifecycle : Common::Lifecycle;
        }
        requirement controllerMass_0007 : Common::MassLimit {
            subject component : Controller_0007;
            attribute :>> limit = 2.0 [kg];
        }
    }

    package Subsystem_0008 {
        part def Sensor_0008 :> Common::Component {
            attribute :>> mass = 0.23 [kg];
            attribute :>> cost = 38.0;
            attribute range : Real = 108.0;
            port data : Common::DataPort;
        }
        part def Controller_0008 :> Common::Component {
            attribute :>> mass = 1.10 [kg];
            attribute :>> cost = 208.0;
            port supply : Common::PowerPort;
            part sensors : Sensor_0008[2];
            action smooth : Common::Process;
            action forward : Common::Process;
            succession first smooth then forward;
            exhibit state lifecycle : Common::Lifecycle;
        }
        requirement controllerMass_0008 : Common::MassLimit {
            subject component : Controller_0008;
            attribute :>> limit = 2.0 [kg];
        }
    }

    package Subsystem_0009 {
        part def Sensor_0009 :> Common::Component {
            attribute :>> mass = 0.24 [kg];
            attribute :>> cost = 39.0;
            attribute range : Real = 109.0;
            port data : Common::DataPort;
        }
        part def Controller_0009 :> Common::Component {
            attribute :>> mass = 1.20 [kg];
            attribute :>> cost = 209.0;
            port supply : Common::PowerPort;
            part sensors : Sensor_0009[2];
            action smooth : Common::Process;
            action forward : Common::Process;
            succession first smooth then forward;
            exhibit state lifecycle : Common::Lifecycle;
        }
        requirement controllerMass_0009 : Common::MassLimit {
            subject component : Controller_0009;
            attribute :>> limit = 2.0 [kg];
        }
    }

    package Subsystem_0010 {
        part def Sensor_0010 :> Common::Component {
            attribute :>> mass = 0.20 [kg];
            attribute :>> cost = 40.0;
            attribute range : Real = 110.0;
            port data : Common::DataPort;
        }
        part def Controller_0010 :> Common::Component {
            attribute :>> mass = 1.30 [kg];
            attribute :>> cost = 210.0;
            port supply : Common::PowerPort;
            part sensors : Sensor_0010[2];
            action smooth : Common::Process;
            action forward : Common::Process;
            succession first smooth then forward;
            exhibit state lifecycle : Common::Lifecycle;
        }
        requirement controllerMass_0010 : Common::MassLimit {
            subject component : Controller_0010;
            attribute :>> limit = 2.0 [kg];
        }
    }

    package Subsystem_0011 {
        part def Sensor_0011 :> Common::Component {
            attribute :>> mass = 0.21 [kg];
            attribute :>> cost = 41.0;
            attribute range : Real = 111.0;
            port data : Common::DataPort;
        }
        part def Controller_0011 :> Common::Component {
            attribute :>> mass = 1.40 [kg];
            attribute :>> cost = 211.0;
            port supply : Common::PowerPort;
            part sensors : Sensor_0011[2];
            action smooth : Common::Process;
            action forward : Common::Process;
            succession first smooth then forward;
            exhibit state lifecycle : Common::Lifecycle;
        }
        requirement controllerMass_0011 : Common::MassLimit {
            subject component : Controller_0011;
            attribute :>> limit = 2.0 [kg];
        }
    }

    package Subsystem_0012 {
        part def Sensor_0012 :> Common::Component {
            attribute :>> mass = 0.22 [kg];
            attribute :>> cost = 42.0;
            attribute range : Real = 112.0;
            port data : Common::DataPort;
        }
        part def Controller_0012 :> Common::Component {
            attribute :>> mass = 1.50 [kg];
            attribute :>> cost = 212.0;
            port supply : Common::PowerPort;
            part sensors : Sensor_0012[2];
            action smooth : Common::Process;
            action forward : Common::Process;
            succession first smooth then forward;
            exhibit state lifecycle : Common::Lifecycle;
        }
        requirement controllerMass_0012 : Common::MassLimit {
            subject component : Controller_0012;
            attribute :>> limit = 2.0 [kg];
        }
    }

    package Subsystem_0013 {
        part def Sensor_0013 :> Common::Component {
            attribute :>> mass = 0.23 [kg];
            attribute :>> cost = 43.0;
            attribute range : Real = 113.0;
            port data : Common::DataPort;
        }
        part def Controller_0013 :> Common::Component {
            attribute :>> mass = 1.60 [kg];
            attribute :>> cost = 213.0;
            port supply : Common::PowerPort;
            part sensors : Sensor_0013[2];
            action smooth : Common::Process;
            action forward : Common::Process;
            succession first smooth then forward;
            exhibit state lifecycle : Common::Lifecycle;
        }
        requirement controllerMass_0013 : Common::MassLimit {
            subject component : Controller_0013;
            attribute :>> limit = 2.0 [kg];
        }
    }

    package Subsystem_0014 {
        part def Sensor_0014 :> Common::Component {
            attribute :>> mass = 0.24 [kg];
            attribute :>> cost = 44.0;
            attribute range : Real = 114.0;
            port data : Common::DataPort;
        }
        part def Controller_0014 :> Common::Component {
            attribute :>> mass = 1.00 [kg];
            attribute :>> cost = 214.0;
            port supply : Common::PowerPort;
            part sensors : Sensor_0014[2];
            action smooth : Common::Process;
            action forward : Common::Process;
            succession first smooth then forward;
            exhibit state lifecycle : Common::Lifecycle;
        }
        requirement controllerMass_0014 : Common::MassLimit {
            subject component : Controller_0014;
            attribute :>> limit = 2.0 [kg];
        }
    }

    package Subsystem_0015 {
        part def Sensor_0015 :> Common::Component {
            attribute :>> mass = 0.20 [kg];
            attribute :>> cost = 45.0;
            attribute range : Real = 115.0;
            port data : Common::DataPort;
        }
        part def Controller_0015 :> Common::Component {
            attribute :>> mass = 1.10 [kg];
            attribute :>> cost = 215.0;
            port supply : Common::PowerPort;
            part sensors : Sensor_0015[2];
            action smooth : Common::Process;
            action forward : Common::Process;
            succession first smooth then forward;
            exhibit state lifecycle : Common::Lifecycle;
        }
        requirement controllerMass_0015 : Common::MassLimit {
            subject component : Controller_0015;
            attribute :>> limit = 2.0 [kg];
        }
    }

    package Subsystem_0016 {
        part def Sensor_0016 :> Common::Component {
            attribute :>> mass = 0.21 [kg];
            attribute :>> cost = 46.0;
            attribute range : Real = 116.0;
            port data : Common::DataPort;
        }
        part def Controller_0016 :> Common::Component {
            attribute :>> mass = 1.20 [kg];
            attribute :>> cost = 216.0;
            port supply : Common::PowerPort;
            part sensors : Sensor_0016[2];
            action smooth : Common::Process;
            action forward : Common::Process;
            succession first smooth then forward;
            exhibit state lifecycle : Common::Lifecycle;
        }
        requirement controllerMass_0016 : Common::MassLimit {
            subject component : Controller_0016;
            attribute :>> limit = 2.0 [kg];
        }
    }

    package Subsystem_0017 {
        part def Sensor_0017 :> Common::Component {
            attribute :>> mass = 0.22 [kg];
            attribute :>> cost = 47.0;
            attribute range : Real = 117.0;
            port data : Common::DataPort;
        }
        part def Controller_0017 :> Common::Component {
            attribute :>> mass = 1.30 [kg];
            attribute :>> cost = 217.0;
            port supply : Common::PowerPort;
            part sensors : Sensor_0017[2];
            action smooth : Common::Process;
            action forward : Common::Process;
            succession first smooth then forward;
            exhibit state lifecycle : Common::Lifecycle;
        }
        requirement controllerMass_0017 : Common::MassLimit {
            subject component : Controller_0017;
            attribute :>> limit = 2.0 [kg];
        }
    }

    package Subsystem_0018 {
        part def Sensor_0018 :> Common::Component {
            attribute :>> mass = 0.23 [kg];
            attribute :>> cost = 48.0;
            attribute range : Real = 118.0;
            port data : Common::DataPort;
        }
        part def Controller_0018 :> Common::Component {
            attribute :>> mass = 1.40 [kg];
            attribute :>> cost = 218.0;
            port supply : Common::PowerPort;
            part sensors : Sensor_0018[2];
            action smooth : Common::Process;
            action forward : Common::Process;
            succession first smooth then forward;
            exhibit state lifecycle : Common::Lifecycle;
        }
        requirement controllerMass_0018 : Common::MassLimit {
            subject component : Controller_0018;
            attribute :>> limit = 2.0 [kg];
        }
    }

    package Subsystem_0019 {
        part def Sensor_0019 :> Common::Component {
            attribute :>> mass = 0.24 [kg];
            attribute :>> cost = 49.0;
            attribute range : Real = 119.0;
            port data : Common::DataPort;
        }
        part def Controller_0019 :> Common::Component {
            attribute :>> mass = 1.50 [kg];
            attribute :>> cost = 219.0;
            port supply : Common::PowerPort;
            part sensors : Sensor_0019[2];
            action smooth : Common::Process;
            action forward : Common::Process;
            succession first smooth then forward;
            exhibit state lifecycle : Common::Lifecycle;
        }
        requirement controllerMass_0019 : Common::MassLimit {
            subject component : Controller_0019;
            attribute :>> limit = 2.0 [kg];
        }
    }

    package Subsystem_0020 {
        part def Sensor_0020 :> Common::Component {
            attribute :>> mass = 0.20 [kg];
            attribute :>> cost = 30.0;
            attribute range : Real = 120.0;
            port data : Common::DataPort;
        }
        part def Controller_0020 :> Common::Component {
            attribute :>> mass = 1.60 [kg];
            attribute :>> cost = 220.0;
            port supply : Common::PowerPort;
            part sensors : Sensor_0020[2];
            action smooth : Common::Process;
            action forward : Common::Process;
            succession first smooth then forward;
            exhibit state lifecycle : Common::Lifecycle;
        }
        requirement controllerMass_0020 : Common::MassLimit {
            subject component : Controller_0020;
            attribute :>> limit = 2.0 [kg];
        }
    }

    package Subsystem_0021 {
        part def Sensor_0021 :> Common::Component {
            attribute :>> mass = 0.21 [kg];
            attribute :>> cost = 31.0;
            attribute range : Real = 121.0;
            port data : Common::DataPort;
        }
        part def Controller_0021 :> Common::Component {
            attribute :>> mass = 1.00 [kg];
            attribute :>> cost = 221.0;
            port supply : Common::PowerPort;
            part sensors : Sensor_0021[2];
            action smooth : Common::Process;
            action forward : Common::Process;
            succession first smooth then forward;
            exhibit state lifecycle : Common::Lifecycle;
        }
        requirement controllerMass_0021 : Common::MassLimit {
            subject component : Controller_0021;
            attribute :>> limit = 2.0 [kg];
        }
    }

    package Subsystem_0022 {
        part def Sensor_0022 :> Common::Component {
            attribute :>> mass = 0.22 [kg];
            attribute :>> cost = 32.0;
            attribute range : Real = 122.0;
            port data : Common::DataPort;
        }
        part def Controller_0022 :> Common::Component {
            attribute :>> mass = 1.10 [kg];
            attribute :>> cost = 222.0;
            port supply : Common::PowerPort;
            part sensors : Sensor_0022[2];
            action smooth : Common::Process;
            action forward : Common::Process;
            succession first smooth then forward;
            exhibit state lifecycle : Common::Lifecycle;
        }
        requirement controllerMass_0022 : Common::MassLimit {
            subject component : Controller_0022;
            attribute :>> limit = 2.0 [kg];
        }
    }

    package Subsystem_0023 {
        part def Sensor_0023 :> Common::Component {
            attribute :>> mass = 0.23 [kg];
            attribute :>> cost = 33.0;
            attribute range : Real = 123.0;
            port data : Common::DataPort;
        }
        part def Controller_0023 :> Common::Component {
            attribute :>> mass = 1.20 [kg];
            attribute :>> cost = 223.0;
            port supply : Common::PowerPort;
            part sensors : Sensor_0023[2];
            action smooth : Common::Process;
            action forward : Common::Process;
            succession first smooth then forward;
            exhibit state lifecycle : Common::Lifecycle;
        }
        requirement controllerMass_0023 : Common::MassLimit {
            subject component : Controller_0023;
            attribute :>> limit = 2.0 [kg];
        }
    }

    package Subsystem_0024 {
        part def Sensor_0024 :> Common::Component {
            attribute :>> mass = 0.24 [kg];
            attribute :>> cost = 34.0;
            attribute range : Real = 124.0;
            port data : Common::DataPort;
        }
        part def Controller_0024 :> Common::Component {
            attribute :>> mass = 1.30 [kg];
            attribute :>> cost = 224.0;
            port supply : Common::PowerPort;
            part sensors : Sensor_0024[2];
            action smooth : Common::Process;
            action forward : Common::Process;
            succession first smooth then forward;
            exhibit state lifecycle : Common::Lifecycle;
        }
        requirement controllerMass_0024 : Common::MassLimit {
            subject component : Controller_0024;
            attribute :>> limit = 2.0 [kg];
        }
    }

    package Subsystem_0025 {
        part def Sensor_0025 :> Common::Component {
            attribute :>> mass = 0.20 [kg];
            attribute :>> cost = 35.0;
            attribute range : Real = 125.0;
            port data : Common::DataPort;
        }
        part def Controller_0025 :> Common::Component {
            attribute :>> mass = 1.40 [kg];
            attribute :>> cost = 225.0;
            port supply : Common::PowerPort;
            part sensors : Sensor_0025[2];
            action smooth : Common::Process;
            action forward : Common::Process;
            succession first smooth then forward;
            exhibit state lifecycle : Common::Lifecycle;
        }
        requirement controllerMass_0025 : Common::MassLimit {
            subject component : Controller_0025;
            attribute :>> limit = 2.0 [kg];
        }
    }

    package Subsystem_0026 {
        part def Sensor_0026 :> Common::Component {
            attribute :>> mass = 0.21 [kg];
            attribute :>> cost = 36.0;
            attribute range : Real = 126.0;
            port data : Common::DataPort;
        }
        part def Controller_0026 :> Common::Component {
            attribute :>> mass = 1.50 [kg];
            attribute :>> cost = 226.0;
            port supply : Common::PowerPort;
            part sensors : Sensor_0026[2];
            action smooth : Common::Process;
            action forward : Common::Process;
            succession first smooth then forward;
            exhibit state lifecycle : Common::Lifecycle;
        }
        requirement controllerMass_0026 : Common::MassLimit {
            subject component : Controller_0026;
            attribute :>> limit = 2.0 [kg];
        }
    }

    package Subsystem_0027 {
        part def Sensor_0027 :> Common::Component {
            attribute :>> mass = 0.22 [kg];
            attribute :>> cost = 37.0;
            attribute range : Real = 127.0;
            port data : Common::DataPort;
        }
        part def Controller_0027 :> Common::Component {
            attribute :>> mass = 1.60 [kg];
            attribute :>> cost = 227.0;
            port supply : Common::PowerPort;
            part sensors : Sensor_0027[2];
            action smooth : Common::Process;
            action forward : Common::Process;
            succession first smooth then forward;
            exhibit state lifecycle : Common::Lifecycle;
        }
        requirement controllerMass_0027 : Common::MassLimit {
            subject component : Controller_0027;
            attribute :>> limit = 2.0 [kg];
        }
    }

    package Subsystem_0028 {
        part def Sensor_0028 :> Common::Component {
            attribute :>> mass = 0.23 [kg];
            attribute :>> cost = 38.0;
            attribute range : Real = 128.0;
            port data : Common::DataPort;
        }
        part def Controller_0028 :> Common::Component {
            attribute :>> mass = 1.00 [kg];
            attribute :>> cost = 228.0;
            port supply : Common::PowerPort;
            part sensors : Sensor_0028[2];
            action smooth : Common::Process;
            action forward : Common::Process;
            succession first smooth then forward;
            exhibit state lifecycle : Common::Lifecycle;
        }
        requirement controllerMass_0028 : Common::MassLimit {
            subject component : Controller_0028;
            attribute :>> limit = 2.0 [kg];
        }
    }

    package Subsystem_0029 {
        part def Sensor_0029 :> Common::Component {
            attribute :>> mass = 0.24 [kg];
            attribute :>> cost = 39.0;
            attribute range : Real = 129.0;
            port data : Common::DataPort;
        }
        part def Controller_0029 :> Common::Component {
            attribute :>> mass = 1.10 [kg];
            attribute :>> cost = 229.0;
            port supply : Common::PowerPort;
            part sensors : Sensor_0029[2];
            action smooth : Common::Process;
            action forward : Common::Process;
            succession first smooth then forward;
            exhibit state lifecycle : Common::Lifecycle;
        }
        requirement controllerMass_0029 : Common::MassLimit {
            subject component : Controller_0029;
            attribute :>> limit = 2.0 [kg];
        }
    }

    package Subsystem_0030 {
        part def Sensor_0030 :> Common::Component {
            attribute :>> mass = 0.20 [kg];
            attribute :>> cost = 40.0;
            attribute range : Real = 130.0;
            port data : Common::DataPort;
        }
        part def Controller_0030 :> Common::Component {
            attribute :>> mass = 1.20 [kg];
            attribute :>> cost = 230.0;
            port supply : Common::PowerPort;
            part sensors : Sensor_0030[2];
            action smooth : Common::Process;
            action forward : Common::Process;
            succession first smooth then forward;
            exhibit state lifecycle : Common::Lifecycle;
        }
        requirement controllerMass_0030 : Common::MassLimit {
            subject component : Controller_0030;
            attribute :>> limit = 2.0 [kg];
        }
    }

    package Subsystem_0031 {
        part def Sensor_0031 :> Common::Component {
            attribute :>> mass = 0.21 [kg];
            attribute :>> cost = 41.0;
            attribute range : Real = 131.0;
            port data : Common::DataPort;
        }
        part def Controller_0031 :> Common::Component {
            attribute :>> mass = 1.30 [kg];
            attribute :>> cost = 231.0;
            port supply : Common::PowerPort;
            part sensors : Sensor_0031[2];
            action smooth : Common::Process;
            action forward : Common::Process;
            succession first smooth then forward;
            exhibit state lifecycle : Common::Lifecycle;
        }
        requirement controllerMass_0031 : Common::MassLimit {
            subject component : Controller_0031;
            attribute :>> limit = 2.0 [kg];
        }
    }

    package Subsystem_0032 {
        part def Sensor_0032 :> Common::Component {
            attribute :>> mass = 0.22 [kg];
            attribute :>> cost = 42.0;
            attribute range : Real = 132.0;
            port data : Common::DataPort;
        }
        part def Controller_0032 :> Common::Component {
            attribute :>> mass = 1.40 [kg];
            attribute :>> cost = 232.0;
            port supply : Common::PowerPort;
            part sensors : Sensor_0032[2];
            action smooth : Common::Process;
            action forward : Common::Process;
            succession first smooth then forward;
            exhibit state lifecycle : Common::Lifecycle;
        }
        requirement controllerMass_0032 : Common::MassLimit {
            subject component : Controller_0032;
            attribute :>> limit = 2.0 [kg];
        }
    }

    package Subsystem_0033 {
        part def Sensor_0033 :> Common::Component {
            attribute :>> mass = 0.23 [kg];
            attribute :>> cost = 43.0;
            attribute range : Real = 133.0;
            port data : Common::DataPort;
        }
        part def Controller_0033 :> Common::Component {
            attribute :>> mass = 1.50 [kg];
            attribute :>> cost = 233.0;
            port supply : Common::PowerPort;
            part sensors : Sensor_0033[2];
            action smooth : Common::Process;
            action forward : Common::Process;
            succession first smooth then forward;
            exhibit state lifecycle : Common::Lifecycle;
        }
        requirement controllerMass_0033 : Common::MassLimit {
            subject component : Controller_0033;
            attribute :>> limit = 2.0 [kg];
        }
    }

    package Subsystem_0034 {
        part def Sensor_0034 :> Common::Component {
            attribute :>> mass = 0.24 [kg];
            attribute :>> cost = 44.0;
            attribute range : Real = 134.0;
            port data : Common::DataPort;
        }
        part def Controller_0034 :> Common::Component {
            attribute :>> mass = 1.60 [kg];
            attribute :>> cost = 234.0;
            port supply : Common::PowerPort;
            part sensors : Sensor_0034[2];
            action smooth : Common::Process;
            action forward : Common::Process;
            succession first smooth then forward;
            exhibit state lifecycle : Common::Lifecycle;
        }
        requirement controllerMass_0034 : Common::MassLimit {
            subject component : Controller_0034;
            attribute :>> limit = 2.0 [kg];
        }
    }

    package Subsystem_0035 {
        part def Sensor_0035 :> Common::Component {
            attribute :>> mass = 0.20 [kg];
            attribute :>> cost = 45.0;
            attribute range : Real = 135.0;
            port data : Common::DataPort;
        }
        part def Controller_0035 :> Common::Component {
            attribute :>> mass = 1.00 [kg];
            attribute :>> cost = 235.0;
            port supply : Common::PowerPort;
            part sensors : Sensor_0035[2];
            action smooth : Common::Process;
            action forward : Common::Process;
            succession first smooth then forward;
            exhibit state lifecycle : Common::Lifecycle;
        }
        requirement controllerMass_0035 : Common::MassLimit {
            subject component : Controller_0035;
            attribute :>> limit = 2.0 [kg];
        }
    }

    package Subsystem_0036 {
        part def Sensor_0036 :> Common::Component {
            attribute :>> mass = 0.21 [kg];
            attribute :>> cost = 46.0;
            attribute range : Real = 136.0;
            port data : Common::DataPort;
        }
        part def Controller_0036 :> Common::Component {
            attribute :>> mass = 1.10 [kg];
            attribute :>> cost = 236.0;
            port supply : Common::PowerPort;
            part sensors : Sensor_0036[2];
            action smooth : Common::Process;
            action forward : Common::Process;
            succession first smooth then forward;
            exhibit state lifecycle : Common::Lifecycle;
        }
        requirement controllerMass_0036 : Common::MassLimit {
            subject component : Controller_0036;
            attribute :>> limit = 2.0 [kg];
        }
    }

    package Subsystem_0037 {
        part def Sensor_0037 :> Common::Component {
            attribute :>> mass = 0.22 [kg];
            attribute :>> cost = 47.0;
            attribute range : Real = 137.0;
            port data : Common::DataPort;
        }
        part def Controller_0037 :> Common::Component {
            attribute :>> mass = 1.20 [kg];
            attribute :>> cost = 237.0;
            port supply : Common::PowerPort;
            part sensors : Sensor_0037[2];
            action smooth : Common::Process;
            action forward : Common::Process;
            succession first smooth then forward;
            exhibit state lifecycle : Common::Lifecycle;
        }
        requirement controllerMass_0037 : Common::MassLimit {
            subject component : Controller_0037;
            attribute :>> limit = 2.0 [kg];
        }
    }

    package Subsystem_0038 {
        part def Sensor_0038 :> Common::Component {
            attribute :>> mass = 0.23 [kg];
            attribute :>> cost = 48.0;
            attribute range : Real = 138.0;
            port data : Common::DataPort;
        }
        part def Controller_0038 :> Common::Component {
            attribute :>> mass = 1.30 [kg];
            attribute :>> cost = 238.0;
            port supply : Common::PowerPort;
            part sensors : Sensor_0038[2];
            action smooth : Common::Process;
            action forward : Common::Process;
            succession first smooth then forward;
            exhibit state lifecycle : Common::Lifecycle;
        }
        requirement controllerMass_0038 : Common::MassLimit {
            subject component : Controller_0038;
            attribute :>> limit = 2.0 [kg];
        }
    }

    package Subsystem_0039 {
        part def Sensor_0039 :> Common::Component {
            attribute :>> mass = 0.24 [kg];
            attribute :>> cost = 49.0;
            attribute range : Real = 139.0;
            port data : Common::DataPort;
        }
        part def Controller_0039 :> Common::Component {
            attribute :>> mass = 1.40 [kg];
            attribute :>> cost = 239.0;
            port supply : Common::PowerPort;
            part sensors : Sensor_0039[2];
            action smooth : Common::Process;
            action forward : Common::Process;
            succession first smooth then forward;
            exhibit state lifecycle : Common::Lifecycle;
        }
        requirement controllerMass_0039 : Common::MassLimit {
            subject component : Controller_0039;
            attribute :>> limit = 2.0 [kg];
        }
    }

    package Subsystem_0040 {
        part def Sensor_0040 :> Common::Component {
            attribute :>> mass = 0.20 [kg];
            attribute :>> cost = 30.0;
            attribute range : Real = 140.0;
            port data : Common::DataPort;
        }
        part def Controller_0040 :> Common::Component {
            attribute :>> mass = 1.50 [kg];
            attribute :>> cost = 240.0;
            port supply : Common::PowerPort;
            part sensors : Sensor_0040[2];
            action smooth : Common::Process;
            action forward : Common::Process;
            succession first smooth then forward;
            exhibit state lifecycle : Common::Lifecycle;
        }
        requirement controllerMass_0040 : Common::MassLimit {
            subject component : Controller_0040;
            attribute :>> limit = 2.0 [kg];
        }
    }

    package Subsystem_0041 {
        part def Sensor_0041 :> Common::Component {
            attribute :>> mass = 0.21 [kg];
            attribute :>> cost = 31.0;
            attribute range : Real = 141.0;
            port data : Common::DataPort;
        }
        part def Controller_0041 :> Common::Component {
            attribute :>> mass = 1.60 [kg];
            attribute :>> cost = 241.0;
            port supply : Common::PowerPort;
            part sensors : Sensor_0041[2];
            action smooth : Common::Process;
            action forward : Common::Process;
            succession first smooth then forward;
            exhibit state lifecycle : Common::Lifecycle;
        }
        requirement controllerMass_0041 : Common::MassLimit {
            subject component : Controller_0041;
            attribute :>> limit = 2.0 [kg];
        }
    }

    package Subsystem_0042 {
        part def Sensor_0042 :> Common::Component {
            attribute :>> mass = 0.22 [kg];
            attribute :>> cost = 32.0;
            attribute range : Real = 142.0;
            port data : Common::DataPort;
        }
        part def Controller_0042 :> Common::Component {
            attribute :>> mass = 1.00 [kg];
            attribute :>> cost = 242.0;
            port supply : Common::PowerPort;
            part sensors : Sensor_0042[2];
            action smooth : Common::Process;
            action forward : Common::Process;
            succession first smooth then forward;
            exhibit state lifecycle : Common::Lifecycle;
        }
        requirement controllerMass_0042 : Common::MassLimit {
            subject component : Controller_0042;
            attribute :>> limit = 2.0 [kg];
        }
    }

    package Subsystem_0043 {
        part def Sensor_0043 :> Common::Component {
            attribute :>> mass = 0.23 [kg];
            attribute :>> cost = 33.0;
            attribute range : Real = 143.0;
            port data : Common::DataPort;
        }
        part def Controller_0043 :> Common::Component {
            attribute :>> mass = 1.10 [kg];
            attribute :>> cost = 243.0;
            port supply : Common::PowerPort;
            part sensors : Sensor_0043[2];
            action smooth : Common::Process;
            action forward : Common::Process;
            succession first smooth then forward;
            exhibit state lifecycle : Common::Lifecycle;
        }
        requirement controllerMass_0043 : Common::MassLimit {
            subject component : Controller_0043;
            attribute :>> limit = 2.0 [kg];
        }
    }

    package Subsystem_0044 {
        part def Sensor_0044 :> Common::Component {
            attribute :>> mass = 0.24 [kg];
            attribute :>> cost = 34.0;
            attribute range : Real = 144.0;
            port data : Common::DataPort;
        }
        part def Controller_0044 :> Common::Component {
            attribute :>> mass = 1.20 [kg];
            attribute :>> cost = 244.0;
            port supply : Common::PowerPort;
            part sensors : Sensor_0044[2];
            action smooth : Common::Process;
            action forward : Common::Process;
            succession first smooth then forward;
            exhibit state lifecycle : Common::Lifecycle;
        }
        requirement controllerMass_0044 : Common::MassLimit {
            subject component : Controller_0044;
            attribute :>> limit = 2.0 [kg];
        }
    }

    package Subsystem_0045 {
        part def Sensor_0045 :> Common::Component {
            attribute :>> mass = 0.20 [kg];
            attribute :>> cost = 35.0;
            attribute range : Real = 145.0;
            port data : Common::DataPort;
        }
        part def Controller_0045 :> Common::Component {
            attribute :>> mass = 1.30 [kg];
            attribute :>> cost = 245.0;
            port supply : Common::PowerPort;
            part sensors : Sensor_0045[2];
            action smooth : Common::Process;
            action forward : Common::Process;
            succession first smooth then forward;
            exhibit state lifecycle : Common::Lifecycle;
        }
        requirement controllerMass_0045 : Common::MassLimit {
            subject component : Controller_0045;
            attribute :>> limit = 2.0 [kg];
        }
    }

    package Subsystem_0046 {
        part def Sensor_0046 :> Common::Component {
            attribute :>> mass = 0.21 [kg];
            attribute :>> cost = 36.0;
            attribute range : Real = 146.0;
            port data : Common::DataPort;
        }
        part def Controller_0046 :> Common::Component {
            attribute :>> mass = 1.40 [kg];
            attribute :>> cost = 246.0;
            port supply : Common::PowerPort;
            part sensors : Sensor_0046[2];
            action smooth : Common::Process;
            action forward : Common::Process;
            succession first smooth then forward;
            exhibit state lifecycle : Common::Lifecycle;
        }
        requirement controllerMass_0046 : Common::MassLimit {
            subject component : Controller_0046;
            attribute :>> limit = 2.0 [kg];
        }
    }

    package Subsystem_0047 {
        part def Sensor_0047 :> Common::Component {
            attribute :>> mass = 0.22 [kg];
            attribute :>> cost = 37.0;
            attribute range : Real = 147.0;
            port data : Common::DataPort;
        }
        part def Controller_0047 :> Common::Component {
            attribute :>> mass = 1.50 [kg];
            attribute :>> cost = 247.0;
            port supply : Common::PowerPort;
            part sensors : Sensor_0047[2];
            action smooth : Common::Process;
            action forward : Common::Process;
            succession first smooth then forward;
            exhibit state lifecycle : Common::Lifecycle;
        }
        requirement controllerMass_0047 : Common::MassLimit {
            subject component : Controller_0047;
            attribute :>> limit = 2.0 [kg];
        }
    }

    package Subsystem_0048 {
        part def Sensor_0048 :> Common::Component {
            attribute :>> mass = 0.23 [kg];
            attribute :>> cost = 38.0;
            attribute range : Real = 148.0;
            port data : Common::DataPort;
        }
        part def Controller_0048 :> Common::Component {
            attribute :>> mass = 1.60 [kg];
            attribute :>> cost = 248.0;
            port supply : Common::PowerPort;
            part sensors : Sensor_0048[2];
            action smooth : Common::Process;
            action forward : Common::Process;
            succession first smooth then forward;
            exhibit state lifecycle : Common::Lifecycle;
        }
        requirement controllerMass_0048 : Common::MassLimit {
            subject component : Controller_0048;
            attribute :>> limit = 2.0 [kg];
        }
    }

    package Subsystem_0049 {
        part def Sensor_0049 :> Common::Component {
            attribute :>> mass = 0.24 [kg];
            attribute :>> cost = 39.0;
            attribute range : Real = 149.0;
            port data : Common::DataPort;
        }
        part def Controller_0049 :> Common::Component {
            attribute :>> mass = 1.00 [kg];
            attribute :>> cost = 249.0;
            port supply : Common::PowerPort;
            part sensors : Sensor_0049[2];
            action smooth : Common::Process;
            action forward : Common::Process;
            succession first smooth then forward;
            exhibit state lifecycle : Common::Lifecycle;
        }
        requirement controllerMass_0049 : Common::MassLimit {
            subject component : Controller_0049;
            attribute :>> limit = 2.0 [kg];
        }
    }

    package Subsystem_0050 {
        part def Sensor_0050 :> Common::Component {
            attribute :>> mass = 0.20 [kg];
            attribute :>> cost = 40.0;
            attribute range : Real = 100.0;
            port data : Common::DataPort;
        }
        part def Controller_0050 :> Common::Component {
            attribute :>> mass = 1.10 [kg];
            attribute :>> cost = 250.0;
            port supply : Common::PowerPort;
            part sensors : Sensor_0050[2];
            action smooth : Common::Process;
            action forward : Common::Process;
            succession first smooth then forward;
            exhibit state lifecycle : Common::Lifecycle;
        }
        requirement controllerMass_0050 : Common::MassLimit {
            subject component : Controller_0050;
            attribute :>> limit = 2.0 [kg];
        }
    }

    package Subsystem_0051 {
        part def Sensor_0051 :> Common::Component {
            attribute :>> mass = 0.21 [kg];
            attribute :>> cost = 41.0;
            attribute range : Real = 101.0;
            port data : Common::DataPort;
        }
        part def Controller_0051 :> Common::Component {
            attribute :>> mass = 1.20 [kg];
            attribute :>> cost = 251.0;
            port supply : Common::PowerPort;
            part sensors : Sensor_0051[2];
            action smooth : Common::Process;
            action forward : Common::Process;
            succession first smooth then forward;
            exhibit state lifecycle : Common::Lifecycle;
        }
        requirement controllerMass_0051 : Common::MassLimit {
            subject component : Controller_0051;
            attribute :>> limit = 2.0 [kg];
        }
    }

    package Subsystem_0052 {
        part def Sensor_0052 :> Common::Component {
            attribute :>> mass = 0.22 [kg];
            attribute :>> cost = 42.0;
            attribute range : Real = 102.0;
            port data : Common::DataPort;
        }
        part def Controller_0052 :> Common::Component {
            attribute :>> mass = 1.30 [kg];
            attribute :>> cost = 252.0;
            port supply : Common::PowerPort;
            part sensors : Sensor_0052[2];
            action smooth : Common::Process;
            action forward : Common::Process;
            succession first smooth then forward;
            exhibit state lifecycle : Common::Lifecycle;
        }
        requirement controllerMass_0052 : Common::MassLimit {
            subject component : Controller_0052;
            attribute :>> limit = 2.0 [kg];
        }
    }

    package Subsystem_0053 {
        part def Sensor_0053 :> Common::Component {
            attribute :>> mass = 0.23 [kg];
            attribute :>> cost = 43.0;
            attribute range : Real = 103.0;
            port data : Common::DataPort;
        }
        part def Controller_0053 :> Common::Component {
            attribute :>> mass = 1.40 [kg];
            attribute :>> cost = 253.0;
            port supply : Common::PowerPort;
            part sensors : Sensor_0053[2];
            action smooth : Common::Process;
            action forward : Common::Process;
            succession first smooth then forward;
            exhibit state lifecycle : Common::Lifecycle;
        }
        requirement controllerMass_0053 : Common::MassLimit {
            subject component : Controller_0053;
            attribute :>> limit = 2.0 [kg];
        }
    }

    package Subsystem_0054 {
        part def Sensor_0054 :> Common::Component {
            attribute :>> mass = 0.24 [kg];
            attribute :>> cost = 44.0;
            attribute range : Real = 104.0;
            port data : Common::DataPort;
        }
        part def Controller_0054 :> Common::Component {
            attribute :>> mass = 1.50 [kg];
            attribute :>> cost = 254.0;
            port supply : Common::PowerPort;
            part sensors : Sensor_0054[2];
            action smooth : Common::Process;
            action forward : Common::Process;
            succession first smooth then forward;
            exhibit state lifecycle : Common::Lifecycle;
        }
        requirement controllerMass_0054 : Common::MassLimit {
            subject component : Controller_0054;
            attribute :>> limit = 2.0 [kg];
        }
    }

    package Subsystem_0055 {
        part def Sensor_0055 :> Common::Component {
            attribute :>> mass = 0.20 [kg];
            attribute :>> cost = 45.0;
            attribute range : Real = 105.0;
            port data : Common::DataPort;
        }
        part def Controller_0055 :> Common::Component {
            attribute :>> mass = 1.60 [kg];
            attribute :>> cost = 255.0;
            port supply : Common::PowerPort;
            part sensors : Sensor_0055[2];
            action smooth : Common::Process;
            action forward : Common::Process;
            succession first smooth then forward;
            exhibit state lifecycle : Common::Lifecycle;
        }
        requirement controllerMass_0055 : Common::MassLimit {
            subject component : Controller_0055;
            attribute :>> limit = 2.0 [kg];
        }
    }

    package Subsystem_0056 {
        part def Sensor_0056 :> Common::Component {
            attribute :>> mass = 0.21 [kg];
            attribute :>> cost = 46.0;
            attribute range : Real = 106.0;
            port data : Common::DataPort;
        }
        part def Controller_0056 :> Common::Component {
            attribute :>> mass = 1.00 [kg];
            attribute :>> cost = 256.0;
            port supply : Common::PowerPort;
            part sensors : Sensor_0056[2];
            action smooth : Common::Process;
            action forward : Common::Process;
            succession first smooth then forward;
            exhibit state lifecycle : Common::Lifecycle;
        }
        requirement controllerMass_0056 : Common::MassLimit {
            subject component : Controller_0056;
            attribute :>> limit = 2.0 [kg];
        }
    }

    package Subsystem_0057 {
        part def Sensor_0057 :> Common::Component {
            attribute :>> mass = 0.22 [kg];
            attribute :>> cost = 47.0;
            attribute range : Real = 107.0;
            port data : Common::DataPort;
        }
        part def Controller_0057 :> Common::Component {
            attribute :>> mass = 1.10 [kg];
            attribute :>> cost = 257.0;
            port supply : Common::PowerPort;
            part sensors : Sensor_0057[2];
            action smooth : Common::Process;
            action forward : Common::Process;
            succession first smooth then forward;
            exhibit state lifecycle : Common::Lifecycle;
        }
        requirement controllerMass_0057 : Common::MassLimit {
            subject component : Controller_0057;
            attribute :>> limit = 2.0 [kg];
        }
    }

    package Subsystem_0058 {
        part def Sensor_0058 :> Common::Component {
            attribute :>> mass = 0.23 [kg];
            attribute :>> cost = 48.0;
            attribute range : Real = 108.0;
            port data : Common::DataPort;
        }
        part def Controller_0058 :> Common::Component {
            attribute :>> mass = 1.20 [kg];
            attribute :>> cost = 258.0;
            port supply : Common::PowerPort;
            part sensors : Sensor_0058[2];
            action smooth : Common::Process;
            action forward : Common::Process;
            succession first smooth then forward;
            exhibit state lifecycle : Common::Lifecycle;
        }
        requirement controllerMass_0058 : Common::MassLimit {
            subject component : Controller_0058;
            attribute :>> limit = 2.0 [kg];
        }
    }

    package Subsystem_0059 {
        part def Sensor_0059 :> Common::Component {
            attribute :>> mass = 0.24 [kg];
            attribute :>> cost = 49.0;
            attribute range : Real = 109.0;
            port data : Common::DataPort;
        }
        part def Controller_0059 :> Common::Component {
            attribute :>> mass = 1.30 [kg];
            attribute :>> cost = 259.0;
            port supply : Common::PowerPort;
            part sensors : Sensor_0059[2];
            action smooth : Common::Process;
            action forward : Common::Process;
            succession first smooth then forward;
            exhibit state lifecycle : Common::Lifecycle;
        }
        requirement controllerMass_0059 : Common::MassLimit {
            subject component : Controller_0059;
            attribute :>> limit = 2.0 [kg];
        }
    }

    package Subsystem_0060 {
        part def Sensor_0060 :> Common::Component {
            attribute :>> mass = 0.20 [kg];
            attribute :>> cost = 30.0;
            attribute range : Real = 110.0;
            port data : Common::DataPort;
        }
        part def Controller_0060 :> Common::Component {
            attribute :>> mass = 1.40 [kg];
            attribute :>> cost = 260.0;
            port supply : Common::PowerPort;
            part sensors : Sensor_0060[2];
            action smooth : Common::Process;
            action forward : Common::Process;
            succession first smooth then forward;
            exhibit state lifecycle : Common::Lifecycle;
        }
        requirement controllerMass_0060 : Common::MassLimit {
            subject component : Controller_0060;
            attribute :>> limit = 2.0 [kg];
        }
    }

    package Subsystem_0061 {
        part def Sensor_0061 :> Common::Component {
            attribute :>> mass = 0.21 [kg];
            attribute :>> cost = 31.0;
            attribute range : Real = 111.0;
            port data : Common::DataPort;
        }
        part def Controller_0061 :> Common::Component {
            attribute :>> mass = 1.50 [kg];
            attribute :>> cost = 261.0;
            port supply : Common::PowerPort;
            part sensors : Sensor_0061[2];
            action smooth : Common::Process;
            action forward : Common::Process;
            succession first smooth then forward;
            exhibit state lifecycle : Common::Lifecycle;
        }
        requirement controllerMass_0061 : Common::MassLimit {
            subject component : Controller_0061;
            attribute :>> limit = 2.0 [kg];
        }
    }

    package Subsystem_0062 {
        part def Sensor_0062 :> Common::Component {
            attribute :>> mass = 0.22 [kg];
            attribute :>> cost = 32.0;
            attribute range : Real = 112.0;
            port data : Common::DataPort;
        }
        part def Controller_0062 :> Common::Component {
            attribute :>> mass = 1.60 [kg];
            attribute :>> cost = 262.0;
            port supply : Common::PowerPort;
            part sensors : Sensor_0062[2];
            action smooth : Common::Process;
            action forward : Common::Process;
            succession first smooth then forward;
            exhibit state lifecycle : Common::Lifecycle;
        }
        requirement controllerMass_0062 : Common::MassLimit {
            subject component : Controller_0062;
            attribute :>> limit = 2.0 [kg];
        }
    }

    package Subsystem_0063 {
        part def Sensor_0063 :> Common::Component {
            attribute :>> mass = 0.23 [kg];
            attribute :>> cost = 33.0;
            attribute range : Real = 113.0;
            port data : Common::DataPort;
        }
        part def Controller_0063 :> Common::Component {
            attribute :>> mass = 1.00 [kg];
            attribute :>> cost = 263.0;
            port supply : Common::PowerPort;
            part sensors : Sensor_0063[2];
            action smooth : Common::Process;
            action forward : Common::Process;
            succession first smooth then forward;
            exhibit state lifecycle : Common::Lifecycle;
        }
        requirement controllerMass_0063 : Common::MassLimit {
            subject component : Controller_0063;
            attribute :>> limit = 2.0 [kg];
        }
    }

    package Subsystem_0064 {
        part def Sensor_0064 :> Common::Component {
            attribute :>> mass = 0.24 [kg];
            attribute :>> cost = 34.0;
            attribute range : Real = 114.0;
            port data : Common::DataPort;
        }
        part def Controller_0064 :> Common::Component {
            attribute :>> mass = 1.10 [kg];
            attribute :>> cost = 264.0;
            port supply : Common::PowerPort;
            part sensors : Sensor_0064[2];
            action smooth : Common::Process;
            action forward : Common::Process;
            succession first smooth then forward;
            exhibit state lifecycle : Common::Lifecycle;
        }
        requirement controllerMass_0064 : Common::MassLimit {
            subject component : Controller_0064;
            attribute :>> limit = 2.0 [kg];
        }
    }

    package Subsystem_0065 {
        part def Sensor_0065 :> Common::Component {
            attribute :>> mass = 0.20 [kg];
            attribute :>> cost = 35.0;
            attribute range : Real = 115.0;
            port data : Common::DataPort;
        }
        part def Controller_0065 :> Common::Component {
            attribute :>> mass = 1.20 [kg];
            attribute :>> cost = 265.0;
            port supply : Common::PowerPort;
            part sensors : Sensor_0065[2];
            action smooth : Common::Process;
            action forward : Common::Process;
            succession first smooth then forward;
            exhibit state lifecycle : Common::Lifecycle;
        }
        requirement controllerMass_0065 : Common::MassLimit {
            subject component : Controller_0065;
            attribute :>> limit = 2.0 [kg];
        }
    }

    package Subsystem_0066 {
        part def Sensor_0066 :> Common::Component {
            attribute :>> mass = 0.21 [kg];
            attribute :>> cost = 36.0;
            attribute range : Real = 116.0;
            port data : Common::DataPort;
        }
        part def Controller_0066 :> Common::Component {
            attribute :>> mass = 1.30 [kg];
            attribute :>> cost = 266.0;
            port supply : Common::PowerPort;
            part sensors : Sensor_0066[2];
            action smooth : Common::Process;
            action forward : Common::Process;
            succession first smooth then forward;
            exhibit state lifecycle : Common::Lifecycle;
        }
        requirement controllerMass_0066 : Common::MassLimit {
            subject component : Controller_0066;
            attribute :>> limit = 2.0 [kg];
        }
    }

    package Subsystem_0067 {
        part def Sensor_0067 :> Common::Component {
            attribute :>> mass = 0.22 [kg];
            attribute :>> cost = 37.0;
            attribute range : Real = 117.0;
            port data : Common::DataPort;
        }
        part def Controller_0067 :> Common::Component {
            attribute :>> mass = 1.40 [kg];
            attribute :>> cost = 267.0;
            port supply : Common::PowerPort;
            part sensors : Sensor_0067[2];
            action smooth : Common::Process;
            action forward : Common::Process;
            succession first smooth then forward;
            exhibit state lifecycle : Common::Lifecycle;
        }
        requirement controllerMass_0067 : Common::MassLimit {
            subject component : Controller_0067;
            attribute :>> limit = 2.0 [kg];
        }
    }

    package Subsystem_0068 {
        part def Sensor_0068 :> Common::Component {
            attribute :>> mass = 0.23 [kg];
            attribute :>> cost = 38.0;
            attribute range : Real = 118.0;
            port data : Common::DataPort;
        }
        part def Controller_0068 :> Common::Component {
            attribute :>> mass = 1.50 [kg];
            attribute :>> cost = 268.0;
            port supply : Common::PowerPort;
            part sensors : Sensor_0068[2];
            action smooth : Common::Process;
            action forward : Common::Process;
            succession first smooth then forward;
            exhibit state lifecycle : Common::Lifecycle;
        }
        requirement controllerMass_0068 : Common::MassLimit {
            subject component : Controller_0068;
            attribute :>> limit = 2.0 [kg];
        }
    }

    package Subsystem_0069 {
        part def Sensor_0069 :> Common::Component {
            attribute :>> mass = 0.24 [kg];
            attribute :>> cost = 39.0;
            attribute range : Real = 119.0;
            port data : Common::DataPort;
        }
        part def Controller_0069 :> Common::Component {
            attribute :>> mass = 1.60 [kg];
            attribute :>> cost = 269.0;
            port supply : Common::PowerPort;
            part sensors : Sensor_0069[2];
            action smooth : Common::Process;
            action forward : Common::Process;
            succession first smooth then forward;
            exhibit state lifecycle : Common::Lifecycle;
        }
        requirement controllerMass_0069 : Common::MassLimit {
            subject component : Controller_0069;
            attribute :>> limit = 2.0 [kg];
        }
    }

    package Subsystem_0070 {
        part def Sensor_0070 :> Common::Component {
            attribute :>> mass = 0.20 [kg];
            attribute :>> cost = 40.0;
            attribute range : Real = 120.0;
            port data : Common::DataPort;
        }
        part def Controller_0070 :> Common::Component {
            attribute :>> mass = 1.00 [kg];
            attribute :>> cost = 270.0;
            port supply : Common::PowerPort;
            part sensors : Sensor_0070[2];
            action smooth : Common::Process;
            action forward : Common::Process;
            succession first smooth then forward;
            exhibit state lifecycle : Common::Lifecycle;
        }
        requirement controllerMass_0070 : Common::MassLimit {
            subject component : Controller_0070;
            attribute :>> limit = 2.0 [kg];
        }
    }

    package Subsystem_0071 {
        part def Sensor_0071 :> Common::Component {
            attribute :>> mass = 0.21 [kg];
            attribute :>> cost = 41.0;
            attribute range : Real = 121.0;
            port data : Common::DataPort;
        }
        part def Controller_0071 :> Common::Component {
            attribute :>> mass = 1.10 [kg];
            attribute :>> cost = 271.0;
            port supply : Common::PowerPort;
            part sensors : Sensor_0071[2];
            action smooth : Common::Process;
            action forward : Common::Process;
            succession first smooth then forward;
            exhibit state lifecycle : Common::Lifecycle;
        }
        requirement controllerMass_0071 : Common::MassLimit {
            subject component : Controller_0071;
            attribute :>> limit = 2.0 [kg];
        }
    }

    package Subsystem_0072 {
        part def Sensor_0072 :> Common::Component {
            attribute :>> mass = 0.22 [kg];
            attribute :>> cost = 42.0;
            attribute range : Real = 122.0;
            port data : Common::DataPort;
        }
        part def Controller_0072 :> Common::Component {
            attribute :>> mass = 1.20 [kg];
            attribute :>> cost = 272.0;
            port supply : Common::PowerPort;
            part sensors : Sensor_0072[2];
            action smooth : Common::Process;
            action forward : Common::Process;
            succession first smooth then forward;
            exhibit state lifecycle : Common::Lifecycle;
        }
        requirement controllerMass_0072 : Common::MassLimit {
            subject component : Controller_0072;
            attribute :>> limit = 2.0 [kg];
        }
    }

    package Subsystem_0073 {
        part def Sensor_0073 :> Common::Component {
            attribute :>> mass = 0.23 [kg];
            attribute :>> cost = 43.0;
            attribute range : Real = 123.0;
            port data : Common::DataPort;
        }
        part def Controller_0073 :> Common::Component {
            attribute :>> mass = 1.30 [kg];
            attribute :>> cost = 273.0;
            port supply : Common::PowerPort;
            part sensors : Sensor_0073[2];
            action smooth : Common::Process;
            action forward : Common::Process;
            succession first smooth then forward;
            exhibit state lifecycle : Common::Lifecycle;
        }
        requirement controllerMass_0073 : Common::MassLimit {
            subject component : Controller_0073;
            attribute :>> limit = 2.0 [kg];
        }
    }

    package Subsystem_0074 {
        part def Sensor_0074 :> Common::Component {
            attribute :>> mass = 0.24 [kg];
            attribute :>> cost = 44.0;
            attribute range : Real = 124.0;
            port data : Common::DataPort;
        }
        part def Controller_0074 :> Common::Component {
            attribute :>> mass = 1.40 [kg];
            attribute :>> cost = 274.0;
            port supply : Common::PowerPort;
            part sensors : Sensor_0074[2];
            action smooth : Common::Process;
            action forward : Common::Process;
            succession first smooth then forward;
            exhibit state lifecycle : Common::Lifecycle;
        }
        requirement controllerMass_0074 : Common::MassLimit {
            subject component : Controller_0074;
            attribute :>> limit = 2.0 [kg];
        }
    }

    package Subsystem_0075 {
        part def Sensor_0075 :> Common::Component {
            attribute :>> mass = 0.20 [kg];
            attribute :>> cost = 45.0;
            attribute range : Real = 125.0;
            port data : Common::DataPort;
        }
        part def Controller_0075 :> Common::Component {
            attribute :>> mass = 1.50 [kg];
            attribute :>> cost = 275.0;
            port supply : Common::PowerPort;
            part sensors : Sensor_0075[2];
            action smooth : Common::Process;
            action forward : Common::Process;
            succession first smooth then forward;
            exhibit state lifecycle : Common::Lifecycle;
        }
        requirement controllerMass_0075 : Common::MassLimit {
            subject component : Controller_0075;
            attribute :>> limit = 2.0 [kg];
        }
    }

    package Subsystem_0076 {
        part def Sensor_0076 :> Common::Component {
            attribute :>> mass = 0.21 [kg];
            attribute :>> cost = 46.0;
            attribute range : Real = 126.0;
            port data : Common::DataPort;
        }
        part def Controller_0076 :> Common::Component {
            attribute :>> mass = 1.60 [kg];
            attribute :>> cost = 276.0;
            port supply : Common::PowerPort;
            part sensors : Sensor_0076[2];
            action smooth : Common::Process;
            action forward : Common::Process;
            succession first smooth then forward;
            exhibit state lifecycle : Common::Lifecycle;
        }
        requirement controllerMass_0076 : Common::MassLimit {
            subject component : Controller_0076;
            attribute :>> limit = 2.0 [kg];
        }
    }

    package Subsystem_0077 {
        part def Sensor_0077 :> Common::Component {
            attribute :>> mass = 0.22 [kg];
            attribute :>> cost = 47.0;
            attribute range : Real = 127.0;
            port data : Common::DataPort;
        }
        part def Controller_0077 :> Common::Component {
            attribute :>> mass = 1.00 [kg];
            attribute :>> cost = 277.0;
            port supply : Common::PowerPort;
            part sensors : Sensor_0077[2];
            action smooth : Common::Process;
            action forward : Common::Process;
            succession first smooth then forward;
            exhibit state lifecycle : Common::Lifecycle;
        }
        requirement controllerMass_0077 : Common::MassLimit {
            subject component : Controller_0077;
            attribute :>> limit = 2.0 [kg];
        }
    }

    package Subsystem_0078 {
        part def Sensor_0078 :> Common::Component {
            attribute :>> mass = 0.23 [kg];
            attribute :>> cost = 48.0;
            attribute range : Real = 128.0;
            port data : Common::DataPort;
        }
        part def Controller_0078 :> Common::Component {
            attribute :>> mass = 1.10 [kg];
            attribute :>> cost = 278.0;
            port supply : Common::PowerPort;
            part sensors : Sensor_0078[2];
            action smooth : Common::Process;
            action forward : Common::Process;
            succession first smooth then forward;
            exhibit state lifecycle : Common::Lifecycle;
        }
        requirement controllerMass_0078 : Common::MassLimit {
            subject component : Controller_0078;
            attribute :>> limit = 2.0 [kg];
        }
    }

    package Subsystem_0079 {
        part def Sensor_0079 :> Common::Component {
            attribute :>> mass = 0.24 [kg];
            attribute :>> cost = 49.0;
            attribute range : Real = 129.0;
            port data : Common::DataPort;
        }
        part def Controller_0079 :> Common::Component {
            attribute :>> mass = 1.20 [kg];
            attribute :>> cost = 279.0;
            port supply : Common::PowerPort;
            part sensors : Sensor_0079[2];
            action smooth : Common::Process;
            action forward : Common::Process;
            succession first smooth then forward;
            exhibit state lifecycle : Common::Lifecycle;
        }
        requirement controllerMass_0079 : Common::MassLimit {
            subject component : Controller_0079;
            attribute :>> limit = 2.0 [kg];
        }
    }

    package Subsystem_0080 {
        part def Sensor_0080 :> Common::Component {
            attribute :>> mass = 0.20 [kg];
            attribute :>> cost = 30.0;
            attribute range : Real = 130.0;
            port data : Common::DataPort;
        }
        part def Controller_0080 :> Common::Component {
            attribute :>> mass = 1.30 [kg];
            attribute :>> cost = 280.0;
            port supply : Common::PowerPort;
            part sensors : Sensor_0080[2];
            action smooth : Common::Process;
            action forward : Common::Process;
            succession first smooth then forward;
            exhibit state lifecycle : Common::Lifecycle;
        }
        requirement controllerMass_0080 : Common::MassLimit {
            subject component : Controller_0080;
            attribute :>> limit = 2.0 [kg];
        }
    }

    package Subsystem_0081 {
        part def Sensor_0081 :> Common::Component {
            attribute :>> mass = 0.21 [kg];
            attribute :>> cost = 31.0;
            attribute range : Real = 131.0;
            port data : Common::DataPort;
        }
        part def Controller_0081 :> Common::Component {
            attribute :>> mass = 1.40 [kg];
            attribute :>> cost = 281.0;
            port supply : Common::PowerPort;
            part sensors : Sensor_0081[2];
            action smooth : Common::Process;
            action forward : Common::Process;
            succession first smooth then forward;
            exhibit state lifecycle : Common::Lifecycle;
        }
        requirement controllerMass_0081 : Common::MassLimit {
            subject component : Controller_0081;
            attribute :>> limit = 2.0 [kg];
        }
    }

    package Subsystem_0082 {
        part def Sensor_0082 :> Common::Component {
            attribute :>> mass = 0.22 [kg];
            attribute :>> cost = 32.0;
            attribute range : Real = 132.0;
            port data : Common::DataPort;
        }
        part def Controller_0082 :> Common::Component {
            attribute :>> mass = 1.50 [kg];
            attribute :>> cost = 282.0;
            port supply : Common::PowerPort;
            part sensors : Sensor_0082[2];
            action smooth : Common::Process;
            action forward : Common::Process;
            succession first smooth then forward;
            exhibit state lifecycle : Common::Lifecycle;
        }
        requirement controllerMass_0082 : Common::MassLimit {
            subject component : Controller_0082;
            attribute :>> limit = 2.0 [kg];
        }
    }

    package Subsystem_0083 {
        part def Sensor_0083 :> Common::Component {
            attribute :>> mass = 0.23 [kg];
            attribute :>> cost = 33.0;
            attribute range : Real = 133.0;
            port data : Common::DataPort;
        }
        part def Controller_0083 :> Common::Component {
            attribute :>> mass = 1.60 [kg];
            attribute :>> cost = 283.0;
            port supply : Common::PowerPort;
            part sensors : Sensor_0083[2];
            action smooth : Common::Process;
            action forward : Common::Process;
            succession first smooth then forward;
            exhibit state lifecycle : Common::Lifecycle;
        }
        requirement controllerMass_0083 : Common::MassLimit {
            subject component : Controller_0083;
            attribute :>> limit = 2.0 [kg];
        }
    }

    package Subsystem_0084 {
        part def Sensor_0084 :> Common::Component {
            attribute :>> mass = 0.24 [kg];
            attribute :>> cost = 34.0;
            attribute range : Real = 134.0;
            port data : Common::DataPort;
        }
        part def Controller_0084 :> Common::Component {
            attribute :>> mass = 1.00 [kg];
            attribute :>> cost = 284.0;
            port supply : Common::PowerPort;
            part sensors : Sensor_0084[2];
            action smooth : Common::Process;
            action forward : Common::Process;
            succession first smooth then forward;
            exhibit state lifecycle : Common::Lifecycle;
        }
        requirement controllerMass_0084 : Common::MassLimit {
            subject component : Controller_0084;
            attribute :>> limit = 2.0 [kg];
        }
    }

    package Subsystem_0085 {
        part def Sensor_0085 :> Common::Component {
            attribute :>> mass = 0.20 [kg];
            attribute :>> cost = 35.0;
            attribute range : Real = 135.0;
            port data : Common::DataPort;
        }
        part def Controller_0085 :> Common::Component {
            attribute :>> mass = 1.10 [kg];
            attribute :>> cost = 285.0;
            port supply : Common::PowerPort;
            part sensors : Sensor_0085[2];
            action smooth : Common::Process;
            action forward : Common::Process;
            succession first smooth then forward;
            exhibit state lifecycle : Common::Lifecycle;
        }
        requirement controllerMass_0085 : Common::MassLimit {
            subject component : Controller_0085;
            attribute :>> limit = 2.0 [kg];
        }
    }

    package Subsystem_0086 {
        part def Sensor_0086 :> Common::Component {
            attribute :>> mass = 0.21 [kg];
            attribute :>> cost = 36.0;
            attribute range : Real = 136.0;
            port data : Common::DataPort;
        }
        part def Controller_0086 :> Common::Component {
            attribute :>> mass = 1.20 [kg];
            attribute :>> cost = 286.0;
            port supply : Common::PowerPort;
            part sensors : Sensor_0086[2];
            action smooth : Common::Process;
            action forward : Common::Process;
            succession first smooth then forward;
            exhibit state lifecycle : Common::Lifecycle;
        }
        requirement controllerMass_0086 : Common::MassLimit {
            subject component : Controller_0086;
            attribute :>> limit = 2.0 [kg];
        }
    }

    package Subsystem_0087 {
        part def Sensor_0087 :> Common::Component {
            attribute :>> mass = 0.22 [kg];
            attribute :>> cost = 37.0;
            attribute range : Real = 137.0;
            port data : Common::DataPort;
        }
        part def Controller_0087 :> Common::Component {
            attribute :>> mass = 1.30 [kg];
            attribute :>> cost = 287.0;
            port supply : Common::PowerPort;
            part sensors : Sensor_0087[2];
            action smooth : Common::Process;
            action forward : Common::Process;
            succession first smooth then forward;
            exhibit state lifecycle : Common::Lifecycle;
        }
        requirement controllerMass_0087 : Common::MassLimit {
            subject component : Controller_0087;
            attribute :>> limit = 2.0 [kg];
        }
    }

    package Subsystem_0088 {
        part def Sensor_0088 :> Common::Component {
            attribute :>> mass = 0.23 [kg];
            attribute :>> cost = 38.0;
            attribute range : Real = 138.0;
            port data : Common::DataPort;
        }
        part def Controller_0088 :> Common::Component {
            attribute :>> mass = 1.40 [kg];
            attribute :>> cost = 288.0;
            port supply : Common::PowerPort;
            part sensors : Sensor_0088[2];
            action smooth : Common::Process;
            action forward : Common::Process;
            succession first smooth then forward;
            exhibit state lifecycle : Common::Lifecycle;
        }
        requirement controllerMass_0088 : Common::MassLimit {
            subject component : Controller_0088;
            attribute :>> limit = 2.0 [kg];
        }
    }

    package Subsystem_0089 {
        part def Sensor_0089 :> Common::Component {
            attribute :>> mass = 0.24 [kg];
            attribute :>> cost = 39.0;
            attribute range : Real = 139.0;
            port data : Common::DataPort;
        }
        part def Controller_0089 :> Common::Component {
            attribute :>> mass = 1.50 [kg];
            attribute :>> cost = 289.0;
            port supply : Common::PowerPort;
            part sensors : Sensor_0089[2];
            action smooth : Common::Process;
            action forward : Common::Process;
            succession first smooth then forward;
            exhibit state lifecycle : Common::Lifecycle;
        }
        requirement controllerMass_0089 : Common::MassLimit {
            subject component : Controller_0089;
            attribute :>> limit = 2.0 [kg];
        }
    }

    package Subsystem_0090 {
        part def Sensor_0090 :> Common::Component {
            attribute :>> mass = 0.20 [kg];
            attribute :>> cost = 40.0;
            attribute range : Real = 140.0;
            port data : Common::DataPort;
        }
        part def Controller_0090 :> Common::Component {
            attribute :>> mass = 1.60 [kg];
            attribute :>> cost = 290.0;
            port supply : Common::PowerPort;
            part sensors : Sensor_0090[2];
            action smooth : Common::Process;
            action forward : Common::Process;
            succession first smooth then forward;
            exhibit state lifecycle : Common::Lifecycle;
        }
        requirement controllerMass_0090 : Common::MassLimit {
            subject component : Controller_0090;
            attribute :>> limit = 2.0 [kg];
        }
    }

    package Subsystem_0091 {
        part def Sensor_0091 :> Common::Component {
            attribute :>> mass = 0.21 [kg];
            attribute :>> cost = 41.0;
            attribute range : Real = 141.0;
            port data : Common::DataPort;
        }
        part def Controller_0091 :> Common::Component {
            attribute :>> mass = 1.00 [kg];
            attribute :>> cost = 291.0;
            port supply : Common::PowerPort;
            part sensors : Sensor_0091[2];
            action smooth : Common::Process;
            action forward : Common::Process;
            succession first smooth then forward;
            exhibit state lifecycle : Common::Lifecycle;
        }
        requirement controllerMass_0091 : Common::MassLimit {
            subject component : Controller_0091;
            attribute :>> limit = 2.0 [kg];
        }
    }

    package Subsystem_0092 {
        part def Sensor_0092 :> Common::Component {
            attribute :>> mass = 0.22 [kg];
            attribute :>> cost = 42.0;
            attribute range : Real = 142.0;
            port data : Common::DataPort;
        }
        part def Controller_0092 :> Common::Component {
            attribute :>> mass = 1.10 [kg];
            attribute :>> cost = 292.0;
            port supply : Common::PowerPort;
            part sensors : Sensor_0092[2];
            action smooth : Common::Process;
            action forward : Common::Process;
            succession first smooth then forward;
            exhibit state lifecycle : Common::Lifecycle;
        }
        requirement controllerMass_0092 : Common::MassLimit {
            subject component : Controller_0092;
            attribute :>> limit = 2.0 [kg];
        }
    }

    package Subsystem_0093 {
        part def Sensor_0093 :> Common::Component {
            attribute :>> mass = 0.23 [kg];
            attribute :>> cost = 43.0;
            attribute range : Real = 143.0;
            port data : Common::DataPort;
        }
        part def Controller_0093 :> Common::Component {
            attribute :>> mass = 1.20 [kg];
            attribute :>> cost = 293.0;
            port supply : Common::PowerPort;
            part sensors : Sensor_0093[2];
            action smooth : Common::Process;
            action forward : Common::Process;
            succession first smooth then forward;
            exhibit state lifecycle : Common::Lifecycle;
        }
        requirement controllerMass_0093 : Common::MassLimit {
            subject component : Controller_0093;
            attribute :>> limit = 2.0 [kg];
        }
    }

    package Subsystem_0094 {
        part def Sensor_0094 :> Common::Component {
            attribute :>> mass = 0.24 [kg];
            attribute :>> cost = 44.0;
            attribute range : Real = 144.0;
            port data : Common::DataPort;
        }
        part def Controller_0094 :> Common::Component {
            attribute :>> mass = 1.30 [kg];
            attribute :>> cost = 294.0;
            port supply : Common::PowerPort;
            part sensors : Sensor_0094[2];
            action smooth : Common::Process;
            action forward : Common::Process;
            succession first smooth then forward;
            exhibit state lifecycle : Common::Lifecycle;
        }
        requirement controllerMass_0094 : Common::MassLimit {
            subject component : Controller_0094;
            attribute :>> limit = 2.0 [kg];
        }
    }

    package Subsystem_0095 {
        part def Sensor_0095 :> Common::Component {
            attribute :>> mass = 0.20 [kg];
            attribute :>> cost = 45.0;
            attribute range : Real = 145.0;
            port data : Common::DataPort;
        }
        part def Controller_0095 :> Common::Component {
            attribute :>> mass = 1.40 [kg];
            attribute :>> cost = 295.0;
            port supply : Common::PowerPort;
            part sensors : Sensor_0095[2];
            action smooth : Common::Process;
            action forward : Common::Process;
            succession first smooth then forward;
            exhibit state lifecycle : Common::Lifecycle;
        }
        requirement controllerMass_0095 : Common::MassLimit {
            subject component : Controller_0095;
            attribute :>> limit = 2.0 [kg];
        }
    }

    package Subsystem_0096 {
        part def Sensor_0096 :> Common::Component {
            attribute :>> mass = 0.21 [kg];
            attribute :>> cost = 46.0;
            attribute range : Real = 146.0;
            port data : Common::DataPort;
        }
        part def Controller_0096 :> Common::Component {
            attribute :>> mass = 1.50 [kg];
            attribute :>> cost = 296.0;
            port supply : Common::PowerPort;
            part sensors : Sensor_0096[2];
            action smooth : Common::Process;
            action forward : Common::Process;
            succession first smooth then forward;
            exhibit state lifecycle : Common::Lifecycle;
        }
        requirement controllerMass_0096 : Common::MassLimit {
            subject component : Controller_0096;
            attribute :>> limit = 2.0 [kg];
        }
    }

    package Subsystem_0097 {
        part def Sensor_0097 :> Common::Component {
            attribute :>> mass = 0.22 [kg];
            attribute :>> cost = 47.0;
            attribute range : Real = 147.0;
            port data : Common::DataPort;
        }
        part def Controller_0097 :> Common::Component {
            attribute :>> mass = 1.60 [kg];
            attribute :>> cost = 297.0;
            port supply : Common::PowerPort;
            part sensors : Sensor_0097[2];
            action smooth : Common::Process;
            action forward : Common::Process;
            succession first smooth then forward;
            exhibit state lifecycle : Common::Lifecycle;
        }
        requirement controllerMass_0097 : Common::MassLimit {
            subject component : Controller_0097;
            attribute :>> limit = 2.0 [kg];
        }
    }

    package Subsystem_0098 {
        part def Sensor_0098 :> Common::Component {
            attribute :>> mass = 0.23 [kg];
            attribute :>> cost = 48.0;
            attribute range : Real = 148.0;
            port data : Common::DataPort;
        }
        part def Controller_0098 :> Common::Component {
            attribute :>> mass = 1.00 [kg];
            attribute :>> cost = 298.0;
            port supply : Common::PowerPort;
            part sensors : Sensor_0098[2];
            action smooth : Common::Process;
            action forward : Common::Process;
            succession first smooth then forward;
            exhibit state lifecycle : Common::Lifecycle;
        }
        requirement controllerMass_0098 : Common::MassLimit {
            subject component : Controller_0098;
            attribute :>> limit = 2.0 [kg];
        }
    }

    package Subsystem_0099 {
        part def Sensor_0099 :> Common::Component {
            attribute :>> mass = 0.24 [kg];
            attribute :>> cost = 49.0;
            attribute range : Real = 149.0;
            port data : Common::DataPort;
        }
        part def Controller_0099 :> Common::Component {
            attribute :>> mass = 1.10 [kg];
            attribute :>> cost = 299.0;
            port supply : Common::PowerPort;
            part sensors : Sensor_0099[2];
            action smooth : Common::Process;
            action forward : Common::Process;
            succession first smooth then forward;
            exhibit state lifecycle : Common::Lifecycle;
        }
        requirement controllerMass_0099 : Common::MassLimit {
            subject component : Controller_0099;
            attribute :>> limit = 2.0 [kg];
        }
    }

    package Subsystem_0100 {
        part def Sensor_0100 :> Common::Component {
            attribute :>> mass = 0.20 [kg];
            attribute :>> cost = 30.0;
            attribute range : Real = 100.0;
            port data : Common::DataPort;
        }
        part def Controller_0100 :> Common::Component {
            attribute :>> mass = 1.20 [kg];
            attribute :>> cost = 200.0;
            port supply : Common::PowerPort;
            part sensors : Sensor_0100[2];
            action smooth : Common::Process;
            action forward : Common::Process;
            succession first smooth then forward;
            exhibit state lifecycle : Common::Lifecycle;
        }
        requirement controllerMass_0100 : Common::MassLimit {
            subject component : Controller_0100;
            attribute :>> limit = 2.0 [kg];
        }
    }

    package Subsystem_0101 {
        part def Sensor_0101 :> Common::Component {
            attribute :>> mass = 0.21 [kg];
            attribute :>> cost = 31.0;
            attribute range : Real = 101.0;
            port data : Common::DataPort;
        }
        part def Controller_0101 :> Common::Component {
            attribute :>> mass = 1.30 [kg];
            attribute :>> cost = 201.0;
            port supply : Common::PowerPort;
            part sensors : Sensor_0101[2];
            action smooth : Common::Process;
            action forward : Common::Process;
            succession first smooth then forward;
            exhibit state lifecycle : Common::Lifecycle;
        }
        requirement controllerMass_0101 : Common::MassLimit {
            subject component : Controller_0101;
            attribute :>> limit = 2.0 [kg];
        }
    }

    package Subsystem_0102 {
        part def Sensor_0102 :> Common::Component {
            attribute :>> mass = 0.22 [kg];
            attribute :>> cost = 32.0;
            attribute range : Real = 102.0;
            port data : Common::DataPort;
        }
        part def Controller_0102 :> Common::Component {
            attribute :>> mass = 1.40 [kg];
            attribute :>> cost = 202.0;
            port supply : Common::PowerPort;
            part sensors : Sensor_0102[2];
            action smooth : Common::Process;
            action forward : Common::Process;
            succession first smooth then forward;
            exhibit state lifecycle : Common::Lifecycle;
        }
        requirement controllerMass_0102 : Common::MassLimit {
            subject component : Controller_0102;
            attribute :>> limit = 2.0 [kg];
        }
    }

    package Subsystem_0103 {
        part def Sensor_0103 :> Common::Component {
            attribute :>> mass = 0.23 [kg];
            attribute :>> cost = 33.0;
            attribute range : Real = 103.0;
            port data : Common::DataPort;
        }
        part def Controller_0103 :> Common::Component {
            attribute :>> mass = 1.50 [kg];
            attribute :>> cost = 203.0;
            port supply : Common::PowerPort;
            part sensors : Sensor_0103[2];
            action smooth : Common::Process;
            action forward : Common::Process;
            succession first smooth then forward;
            exhibit state lifecycle : Common::Lifecycle;
        }
        requirement controllerMass_0103 : Common::MassLimit {
            subject component : Controller_0103;
            attribute :>> limit = 2.0 [kg];
        }
    }

    package Subsystem_0104 {
        part def Sensor_0104 :> Common::Component {
            attribute :>> mass = 0.24 [kg];
            attribute :>> cost = 34.0;
            attribute range : Real = 104.0;
            port data : Common::DataPort;
        }
        part def Controller_0104 :> Common::Component {
            attribute :>> mass = 1.60 [kg];
            attribute :>> cost = 204.0;
            port supply : Common::PowerPort;
            part sensors : Sensor_0104[2];
            action smooth : Common::Process;
            action forward : Common::Process;
            succession first smooth then forward;
            exhibit state lifecycle : Common::Lifecycle;
        }
        requirement controllerMass_0104 : Common::MassLimit {
            subject component : Controller_0104;
            attribute :>> limit = 2.0 [kg];
        }
    }

    package Subsystem_0105 {
        part def Sensor_0105 :> Common::Component {
            attribute :>> mass = 0.20 [kg];
            attribute :>> cost = 35.0;
            attribute range : Real = 105.0;
            port data : Common::DataPort;
        }
        part def Controller_0105 :> Common::Component {
            attribute :>> mass = 1.00 [kg];
            attribute :>> cost = 205.0;
            port supply : Common::PowerPort;
            part sensors : Sensor_0105[2];
            action smooth : Common::Process;
            action forward : Common::Process;
            succession first smooth then forward;
            exhibit state lifecycle : Common::Lifecycle;
        }
        requirement controllerMass_0105 : Common::MassLimit {
            subject component : Controller_0105;
            attribute :>> limit = 2.0 [kg];
        }
    }

    package Subsystem_0106 {
        part def Sensor_0106 :> Common::Component {
            attribute :>> mass = 0.21 [kg];
            attribute :>> cost = 36.0;
            attribute range : Real = 106.0;
            port data : Common::DataPort;
        }
        part def Controller_0106 :> Common::Component {
            attribute :>> mass = 1.10 [kg];
            attribute :>> cost = 206.0;
            port supply : Common::PowerPort;
            part sensors : Sensor_0106[2];
            action smooth : Common::Process;
            action forward : Common::Process;
            succession first smooth then forward;
            exhibit state lifecycle : Common::Lifecycle;
        }
        requirement controllerMass_0106 : Common::MassLimit {
            subject component : Controller_0106;
            attribute :>> limit = 2.0 [kg];
        }
    }

    package Subsystem_0107 {
        part def Sensor_0107 :> Common::Component {
            attribute :>> mass = 0.22 [kg];
            attribute :>> cost = 37.0;
            attribute range : Real = 107.0;
            port data : Common::DataPort;
        }
        part def Controller_0107 :> Common::Component {
            attribute :>> mass = 1.20 [kg];
            attribute :>> cost = 207.0;
            port supply : Common::PowerPort;
            part sensors : Sensor_0107[2];
            action smooth : Common::Process;
            action forward : Common::Process;
            succession first smooth then forward;
            exhibit state lifecycle : Common::Lifecycle;
        }
        requirement controllerMass_0107 : Common::MassLimit {
            subject component : Controller_0107;
            attribute :>> limit = 2.0 [kg];
        }
    }

    package Subsystem_0108 {
        part def Sensor_0108 :> Common::Component {
            attribute :>> mass = 0.23 [kg];
            attribute :>> cost = 38.0;
            attribute range : Real = 108.0;
            port data : Common::DataPort;
        }
        part def Controller_0108 :> Common::Component {
            attribute :>> mass = 1.30 [kg];
            attribute :>> cost = 208.0;
            port supply : Common::PowerPort;
            part sensors : Sensor_0108[2];
            action smooth : Common::Process;
            action forward : Common::Process;
            succession first smooth then forward;
            exhibit state lifecycle : Common::Lifecycle;
        }
        requirement controllerMass_0108 : Common::MassLimit {
            subject component : Controller_0108;
            attribute :>> limit = 2.0 [kg];
        }
    }

    package Subsystem_0109 {
        part def Sensor_0109 :> Common::Component {
            attribute :>> mass = 0.24 [kg];
            attribute :>> cost = 39.0;
            attribute range : Real = 109.0;
            port data : Common::DataPort;
        }
        part def Controller_0109 :> Common::Component {
            attribute :>> mass = 1.40 [kg];
            attribute :>> cost = 209.0;
            port supply : Common::PowerPort;
            part sensors : Sensor_0109[2];
            action smooth : Common::Process;
            action forward : Common::Process;
            succession first smooth then forward;
            exhibit state lifecycle : Common::Lifecycle;
        }
        requirement controllerMass_0109 : Common::MassLimit {
            subject component : Controller_0109;
            attribute :>> limit = 2.0 [kg];
        }
    }

    package Subsystem_0110 {
        part def Sensor_0110 :> Common::Component {
            attribute :>> mass = 0.20 [kg];
            attribute :>> cost = 40.0;
            attribute range : Real = 110.0;
            port data : Common::DataPort;
        }
        part def Controller_0110 :> Common::Component {
            attribute :>> mass = 1.50 [kg];
            attribute :>> cost = 210.0;
            port supply : Common::PowerPort;
            part sensors : Sensor_0110[2];
            action smooth : Common::Process;
            action forward : Common::Process;
            succession first smooth then forward;
            exhibit state lifecycle : Common::Lifecycle;
        }
        requirement controllerMass_0110 : Common::MassLimit {
            subject component : Controller_0110;
            attribute :>> limit = 2.0 [kg];
        }
    }

    package Subsystem_0111 {
        part def Sensor_0111 :> Common::Component {
            attribute :>> mass = 0.21 [kg];
            attribute :>> cost = 41.0;
            attribute range : Real = 111.0;
            port data : Common::DataPort;
        }
        part def Controller_0111 :> Common::Component {
            attribute :>> mass = 1.60 [kg];
            attribute :>> cost = 211.0;
            port supply : Common::PowerPort;
            part sensors : Sensor_0111[2];
            action smooth : Common::Process;
            action forward : Common::Process;
            succession first smooth then forward;
            exhibit state lifecycle : Common::Lifecycle;
        }
        requirement controllerMass_0111 : Common::MassLimit {
            subject component : Controller_0111;
            attribute :>> limit = 2.0 [kg];
        }
    }

    package Subsystem_0112 {
        part def Sensor_0112 :> Common::Component {
            attribute :>> mass = 0.22 [kg];
            attribute :>> cost = 42.0;
            attribute range : Real = 112.0;
            port data : Common::DataPort;
        }
        part def Controller_0112 :> Common::Component {
            attribute :>> mass = 1.00 [kg];
            attribute :>> cost = 212.0;
            port supply : Common::PowerPort;
            part sensors : Sensor_0112[2];
            action smooth : Common::Process;
            action forward : Common::Process;
            succession first smooth then forward;
            exhibit state lifecycle : Common::Lifecycle;
        }
        requirement controllerMass_0112 : Common::MassLimit {
            subject component : Controller_0112;
            attribute :>> limit = 2.0 [kg];
        }
    }

    package Subsystem_0113 {
        part def Sensor_0113 :> Common::Component {
            attribute :>> mass = 0.23 [kg];
            attribute :>> cost = 43.0;
            attribute range : Real = 113.0;
            port data : Common::DataPort;
        }
        part def Controller_0113 :> Common::Component {
            attribute :>> mass = 1.10 [kg];
            attribute :>> cost = 213.0;
            port supply : Common::PowerPort;
            part sensors : Sensor_0113[2];
            action smooth : Common::Process;
            action forward : Common::Process;
            succession first smooth then forward;
            exhibit state lifecycle : Common::Lifecycle;
        }
        requirement controllerMass_0113 : Common::MassLimit {
            subject component : Controller_0113;
            attribute :>> limit = 2.0 [kg];
        }
    }

    package Subsystem_0114 {
        part def Sensor_0114 :> Common::Component {
            attribute :>> mass = 0.24 [kg];
            attribute :>> cost = 44.0;
            attribute range : Real = 114.0;
            port data : Common::DataPort;
        }
        part def Controller_0114 :> Common::Component {
            attribute :>> mass = 1.20 [kg];
            attribute :>> cost = 214.0;
            port supply : Common::PowerPort;
            part sensors : Sensor_0114[2];
            action smooth : Common::Process;
            action forward : Common::Process;
            succession first smooth then forward;
            exhibit state lifecycle : Common::Lifecycle;
        }
        requirement controllerMass_0114 : Common::MassLimit {
            subject component : Controller_0114;
            attribute :>> limit = 2.0 [kg];
        }
    }

    package Subsystem_0115 {
        part def Sensor_0115 :> Common::Component {
            attribute :>> mass = 0.20 [kg];
            attribute :>> cost = 45.0;
            attribute range : Real = 115.0;
            port data : Common::DataPort;
        }
        part def Controller_0115 :> Common::Component {
            attribute :>> mass = 1.30 [kg];
            attribute :>> cost = 215.0;
            port supply : Common::PowerPort;
            part sensors : Sensor_0115[2];
            action smooth : Common::Process;
            action forward : Common::Process;
            succession first smooth then forward;
            exhibit state lifecycle : Common::Lifecycle;
        }
        requirement controllerMass_0115 : Common::MassLimit {
            subject component : Controller_0115;
            attribute :>> limit = 2.0 [kg];
        }
    }

    package Subsystem_0116 {
        part def Sensor_0116 :> Common::Component {
            attribute :>> mass = 0.21 [kg];
            attribute :>> cost = 46.0;
            attribute range : Real = 116.0;
            port data : Common::DataPort;
        }
        part def Controller_0116 :> Common::Component {
            attribute :>> mass = 1.40 [kg];
            attribute :>> cost = 216.0;
            port supply : Common::PowerPort;
            part sensors : Sensor_0116[2];
            action smooth : Common::Process;
            action forward : Common::Process;
            succession first smooth then forward;
            exhibit state lifecycle : Common::Lifecycle;
        }
        requirement controllerMass_0116 : Common::MassLimit {
            subject component : Controller_0116;
            attribute :>> limit = 2.0 [kg];
        }
    }

    package Subsystem_0117 {
        part def Sensor_0117 :> Common::Component {
            attribute :>> mass = 0.22 [kg];
            attribute :>> cost = 47.0;
            attribute range : Real = 117.0;
            port data : Common::DataPort;
        }
        part def Controller_0117 :> Common::Component {
            attribute :>> mass = 1.50 [kg];
            attribute :>> cost = 217.0;
            port supply : Common::PowerPort;
            part sensors : Sensor_0117[2];
            action smooth : Common::Process;
            action forward : Common::Process;
            succession first smooth then forward;
            exhibit state lifecycle : Common::Lifecycle;
        }
        requirement controllerMass_0117 : Common::MassLimit {
            subject component : Controller_0117;
            attribute :>> limit = 2.0 [kg];
        }
    }

    package Subsystem_0118 {
        part def Sensor_0118 :> Common::Component {
            attribute :>> mass = 0.23 [kg];
            attribute :>> cost = 48.0;
            attribute range : Real = 118.0;
            port data : Common::DataPort;
        }
        part def Controller_0118 :> Common::Component {
            attribute :>> mass = 1.60 [kg];
            attribute :>> cost = 218.0;
            port supply : Common::PowerPort;
            part sensors : Sensor_0118[2];
            action smooth : Common::Process;
            action forward : Common::Process;
            succession first smooth then forward;
            exhibit state lifecycle : Common::Lifecycle;
        }
        requirement controllerMass_0118 : Common::MassLimit {
            subject component : Controller_0118;
            attribute :>> limit = 2.0 [kg];
        }
    }

    package Subsystem_0119 {
        part def Sensor_0119 :> Common::Component {
            attribute :>> mass = 0.24 [kg];
            attribute :>> cost = 49.0;
            attribute range : Real = 119.0;
            port data : Common::DataPort;
        }
        part def Controller_0119 :> Common::Component {
            attribute :>> mass = 1.00 [kg];
            attribute :>> cost = 219.0;
            port supply : Common::PowerPort;
            part sensors : Sensor_0119[2];
            action smooth : Common::Process;
            action forward : Common::Process;
            succession first smooth then forward;
            exhibit state lifecycle : Common::Lifecycle;
        }
        requirement controllerMass_0119 : Common::MassLimit {
            subject component : Controller_0119;
            attribute :>> limit = 2.0 [kg];
        }
    }

    package Subsystem_0120 {
        part def Sensor_0120 :> Common::Component {
            attribute :>> mass = 0.20 [kg];
            attribute :>> cost = 30.0;
            attribute range : Real = 120.0;
            port data : Common::DataPort;
        }
        part def Controller_0120 :> Common::Component {
            attribute :>> mass = 1.10 [kg];
            attribute :>> cost = 220.0;
            port supply : Common::PowerPort;
            part sensors : Sensor_0120[2];
            action smooth : Common::Process;
            action forward : Common::Process;
            succession first smooth then forward;
            exhibit state lifecycle : Common::Lifecycle;
        }
        requirement controllerMass_0120 : Common::MassLimit {
            subject component : Controller_0120;
            attribute :>> limit = 2.0 [kg];
        }
    }

    package Subsystem_0121 {
        part def Sensor_0121 :> Common::Component {
            attribute :>> mass = 0.21 [kg];
            attribute :>> cost = 31.0;
            attribute range : Real = 121.0;
            port data : Common::DataPort;
        }
        part def Controller_0121 :> Common::Component {
            attribute :>> mass = 1.20 [kg];
            attribute :>> cost = 221.0;
            port supply : Common::PowerPort;
            part sensors : Sensor_0121[2];
            action smooth : Common::Process;
            action forward : Common::Process;
            succession first smooth then forward;
            exhibit state lifecycle : Common::Lifecycle;
        }
        requirement controllerMass_0121 : Common::MassLimit {
            subject component : Controller_0121;
            attribute :>> limit = 2.0 [kg];
        }
    }

    package Subsystem_0122 {
        part def Sensor_0122 :> Common::Component {
            attribute :>> mass = 0.22 [kg];
            attribute :>> cost = 32.0;
            attribute range : Real = 122.0;
            port data : Common::DataPort;
        }
        part def Controller_0122 :> Common::Component {
            attribute :>> mass = 1.30 [kg];
            attribute :>> cost = 222.0;
            port supply : Common::PowerPort;
            part sensors : Sensor_0122[2];
            action smooth : Common::Process;
            action forward : Common::Process;
            succession first smooth then forward;
            exhibit state lifecycle : Common::Lifecycle;
        }
        requirement controllerMass_0122 : Common::MassLimit {
            subject component : Controller_0122;
            attribute :>> limit = 2.0 [kg];
        }
    }

    package Subsystem_0123 {
        part def Sensor_0123 :> Common::Component {
            attribute :>> mass = 0.23 [kg];
            attribute :>> cost = 33.0;
            attribute range : Real = 123.0;
            port data : Common::DataPort;
        }
        part def Controller_0123 :> Common::Component {
            attribute :>> mass = 1.40 [kg];
            attribute :>> cost = 223.0;
            port supply : Common::PowerPort;
            part sensors : Sensor_0123[2];
            action smooth : Common::Process;
            action forward : Common::Process;
            succession first smooth then forward;
            exhibit state lifecycle : Common::Lifecycle;
        }
        requirement controllerMass_0123 : Common::MassLimit {
            subject component : Controller_0123;
            attribute :>> limit = 2.0 [kg];
        }
    }

    package Subsystem_0124 {
        part def Sensor_0124 :> Common::Component {
            attribute :>> mass = 0.24 [kg];
            attribute :>> cost = 34.0;
            attribute range : Real = 124.0;
            port data : Common::DataPort;
        }
        part def Controller_0124 :> Common::Component {
            attribute :>> mass = 1.50 [kg];
            attribute :>> cost = 224.0;
            port supply : Common::PowerPort;
            part sensors : Sensor_0124[2];
            action smooth : Common::Process;
            action forward : Common::Process;
            succession first smooth then forward;
            exhibit state lifecycle : Common::Lifecycle;
        }
        requirement controllerMass_0124 : Common::MassLimit {
            subject component : Controller_0124;
            attribute :>> limit = 2.0 [kg];
        }
    }

    package Subsystem_0125 {
        part def Sensor_0125 :> Common::Component {
            attribute :>> mass = 0.20 [kg];
            attribute :>> cost = 35.0;
            attribute range : Real = 125.0;
            port data : Common::DataPort;
        }
        part def Controller_0125 :> Common::Component {
            attribute :>> mass = 1.60 [kg];
            attribute :>> cost = 225.0;
            port supply : Common::PowerPort;
            part sensors : Sensor_0125[2];
            action smooth : Common::Process;
            action forward : Common::Process;
            succession first smooth then forward;
            exhibit state lifecycle : Common::Lifecycle;
        }
        requirement controllerMass_0125 : Common::MassLimit {
            subject component : Controller_0125;
            attribute :>> limit = 2.0 [kg];
        }
    }

    package Subsystem_0126 {
        part def Sensor_0126 :> Common::Component {
            attribute :>> mass = 0.21 [kg];
            attribute :>> cost = 36.0;
            attribute range : Real = 126.0;
            port data : Common::DataPort;
        }
        part def Controller_0126 :> Common::Component {
            attribute :>> mass = 1.00 [kg];
            attribute :>> cost = 226.0;
            port supply : Common::PowerPort;
            part sensors : Sensor_0126[2];
            action smooth : Common::Process;
            action forward : Common::Process;
            succession first smooth then forward;
            exhibit state lifecycle : Common::Lifecycle;
        }
        requirement controllerMass_0126 : Common::MassLimit {
            subject component : Controller_0126;
            attribute :>> limit = 2.0 [kg];
        }
    }

    package Subsystem_0127 {
        part def Sensor_0127 :> Common::Component {
            attribute :>> mass = 0.22 [kg];
            attribute :>> cost = 37.0;
            attribute range : Real = 127.0;
            port data : Common::DataPort;
        }
        part def Controller_0127 :> Common::Component {
            attribute :>> mass = 1.10 [kg];
            attribute :>> cost = 227.0;
            port supply : Common::PowerPort;
            part sensors : Sensor_0127[2];
            action smooth : Common::Process;
            action forward : Common::Process;
            succession first smooth then forward;
            exhibit state lifecycle : Common::Lifecycle;
        }
        requirement controllerMass_0127 : Common::MassLimit {
            subject component : Controller_0127;
            attribute :>> limit = 2.0 [kg];
        }
    }

    package Subsystem_0128 {
        part def Sensor_0128 :> Common::Component {
            attribute :>> mass = 0.23 [kg];
            attribute :>> cost = 38.0;
            attribute range : Real = 128.0;
            port data : Common::DataPort;
        }
        part def Controller_0128 :> Common::Component {
            attribute :>> mass = 1.20 [kg];
            attribute :>> cost = 228.0;
            port supply : Common::PowerPort;
            part sensors : Sensor_0128[2];
            action smooth : Common::Process;
            action forward : Common::Process;
            succession first smooth then forward;
            exhibit state lifecycle : Common::Lifecycle;
        }
        requirement controllerMass_0128 : Common::MassLimit {
            subject component : Controller_0128;
            attribute :>> limit = 2.0 [kg];
        }
    }

    package Subsystem_0129 {
        part def Sensor_0129 :> Common::Component {
            attribute :>> mass = 0.24 [kg];
            attribute :>> cost = 39.0;
            attribute range : Real = 129.0;
            port data : Common::DataPort;
        }
        part def Controller_0129 :> Common::Component {
            attribute :>> mass = 1.30 [kg];
            attribute :>> cost = 229.0;
            port supply : Common::PowerPort;
            part sensors : Sensor_0129[2];
            action smooth : Common::Process;
            action forward : Common::Process;
            succession first smooth then forward;
            exhibit state lifecycle : Common::Lifecycle;
        }
        requirement controllerMass_0129 : Common::MassLimit {
            subject component : Controller_0129;
            attribute :>> limit = 2.0 [kg];
        }
    }

    package Subsystem_0130 {
        part def Sensor_0130 :> Common::Component {
            attribute :>> mass = 0.20 [kg];
            attribute :>> cost = 40.0;
            attribute range : Real = 130.0;
            port data : Common::DataPort;
        }
        part def Controller_0130 :> Common::Component {
            attribute :>> mass = 1.40 [kg];
            attribute :>> cost = 230.0;
            port supply : Common::PowerPort;
            part sensors : Sensor_0130[2];
            action smooth : Common::Process;
            action forward : Common::Process;
            succession first smooth then forward;
            exhibit state lifecycle : Common::Lifecycle;
        }
        requirement controllerMass_0130 : Common::MassLimit {
            subject component : Controller_0130;
            attribute :>> limit = 2.0 [kg];
        }
    }

    package Subsystem_0131 {
        part def Sensor_0131 :> Common::Component {
            attribute :>> mass = 0.21 [kg];
            attribute :>> cost = 41.0;
            attribute range : Real = 131.0;
            port data : Common::DataPort;
        }
        part def Controller_0131 :> Common::Component {
            attribute :>> mass = 1.50 [kg];
            attribute :>> cost = 231.0;
            port supply : Common::PowerPort;
            part sensors : Sensor_0131[2];
            action smooth : Common::Process;
            action forward : Common::Process;
            succession first smooth then forward;
            exhibit state lifecycle : Common::Lifecycle;
        }
        requirement controllerMass_0131 : Common::MassLimit {
            subject component : Controller_0131;
            attribute :>> limit = 2.0 [kg];
        }
    }

    package Subsystem_0132 {
        part def Sensor_0132 :> Common::Component {
            attribute :>> mass = 0.22 [kg];
            attribute :>> cost = 42.0;
            attribute range : Real = 132.0;
            port data : Common::DataPort;
        }
        part def Controller_0132 :> Common::Component {
            attribute :>> mass = 1.60 [kg];
            attribute :>> cost = 232.0;
            port supply : Common::PowerPort;
            part sensors : Sensor_0132[2];
            action smooth : Common::Process;
            action forward : Common::Process;
            succession first smooth then forward;
            exhibit state lifecycle : Common::Lifecycle;
        }
        requirement controllerMass_0132 : Common::MassLimit {
            subject component : Controller_0132;
            attribute :>> limit = 2.0 [kg];
        }
    }

    package Subsystem_0133 {
        part def Sensor_0133 :> Common::Component {
            attribute :>> mass = 0.23 [kg];
            attribute :>> cost = 43.0;
            attribute range : Real = 133.0;
            port data : Common::DataPort;
        }
        part def Controller_0133 :> Common::Component {
            attribute :>> mass = 1.00 [kg];
            attribute :>> cost = 233.0;
            port supply : Common::PowerPort;
            part sensors : Sensor_0133[2];
            action smooth : Common::Process;
            action forward : Common::Process;
            succession first smooth then forward;
            exhibit state lifecycle : Common::Lifecycle;
        }
        requirement controllerMass_0133 : Common::MassLimit {
            subject component : Controller_0133;
            attribute :>> limit = 2.0 [kg];
        }
    }

    package Subsystem_0134 {
        part def Sensor_0134 :> Common::Component {
            attribute :>> mass = 0.24 [kg];
            attribute :>> cost = 44.0;
            attribute range : Real = 134.0;
            port data : Common::DataPort;
        }
        part def Controller_0134 :> Common::Component {
            attribute :>> mass = 1.10 [kg];
            attribute :>> cost = 234.0;
            port supply : Common::PowerPort;
            part sensors : Sensor_0134[2];
            action smooth : Common::Process;
            action forward : Common::Process;
            succession first smooth then forward;
            exhibit state lifecycle : Common::Lifecycle;
        }
        requirement controllerMass_0134 : Common::MassLimit {
            subject component : Controller_0134;
            attribute :>> limit = 2.0 [kg];
        }
    }

    package Subsystem_0135 {
        part def Sensor_0135 :> Common::Component {
            attribute :>> mass = 0.20 [kg];
            attribute :>> cost = 45.0;
            attribute range : Real = 135.0;
            port data : Common::DataPort;
        }
        part def Controller_0135 :> Common::Component {
            attribute :>> mass = 1.20 [kg];
            attribute :>> cost = 235.0;
            port supply : Common::PowerPort;
            part sensors : Sensor_0135[2];
            action smooth : Common::Process;
            action forward : Common::Process;
            succession first smooth then forward;
            exhibit state lifecycle : Common::Lifecycle;
        }
        requirement controllerMass_0135 : Common::MassLimit {
            subject component : Controller_0135;
            attribute :>> limit = 2.0 [kg];
        }
    }

    package Subsystem_0136 {
        part def Sensor_0136 :> Common::Component {
            attribute :>> mass = 0.21 [kg];
            attribute :>> cost = 46.0;
            attribute range : Real = 136.0;
            port data : Common::DataPort;
        }
        part def Controller_0136 :> Common::Component {
            attribute :>> mass = 1.30 [kg];
            attribute :>> cost = 236.0;
            port supply : Common::PowerPort;
            part sensors : Sensor_0136[2];
            action smooth : Common::Process;
            action forward : Common::Process;
            succession first smooth then forward;
            exhibit state lifecycle : Common::Lifecycle;
        }
        requirement controllerMass_0136 : Common::MassLimit {
            subject component : Controller_0136;
            attribute :>> limit = 2.0 [kg];
        }
    }

    package Subsystem_0137 {
        part def Sensor_0137 :> Common::Component {
            attribute :>> mass = 0.22 [kg];
            attribute :>> cost = 47.0;
            attribute range : Real = 137.0;
            port data : Common::DataPort;
        }
        part def Controller_0137 :> Common::Component {
            attribute :>> mass = 1.40 [kg];
            attribute :>> cost = 237.0;
            port supply : Common::PowerPort;
            part sensors : Sensor_0137[2];
            action smooth : Common::Process;
            action forward : Common::Process;
            succession first smooth then forward;
            exhibit state lifecycle : Common::Lifecycle;
        }
        requirement controllerMass_0137 : Common::MassLimit {
            subject component : Controller_0137;
            attribute :>> limit = 2.0 [kg];
        }
    }

    package Subsystem_0138 {
        part def Sensor_0138 :> Common::Component {
            attribute :>> mass = 0.23 [kg];
            attribute :>> cost = 48.0;
            attribute range : Real = 138.0;
            port data : Common::DataPort;
        }
        part def Controller_0138 :> Common::Component {
            attribute :>> mass = 1.50 [kg];
            attribute :>> cost = 238.0;
            port supply : Common::PowerPort;
            part sensors : Sensor_0138[2];
            action smooth : Common::Process;
            action forward : Common::Process;
            succession first smooth then forward;
            exhibit state lifecycle : Common::Lifecycle;
        }
        requirement controllerMass_0138 : Common::MassLimit {
            subject component : Controller_0138;
            attribute :>> limit = 2.0 [kg];
        }
    }

    package Subsystem_0139 {
        part def Sensor_0139 :> Common::Component {
            attribute :>> mass = 0.24 [kg];
            attribute :>> cost = 49.0;
            attribute range : Real = 139.0;
            port data : Common::DataPort;
        }
        part def Controller_0139 :> Common::Component {
            attribute :>> mass = 1.60 [kg];
            attribute :>> cost = 239.0;
            port supply : Common::PowerPort;
            part sensors : Sensor_0139[2];
            action smooth : Common::Process;
            action forward : Common::Process;
            succession first smooth then forward;
            exhibit state lifecycle : Common::Lifecycle;
        }
        requirement controllerMass_0139 : Common::MassLimit {
            subject component : Controller_0139;
            attribute :>> limit = 2.0 [kg];
        }
    }

    package Subsystem_0140 {
        part def Sensor_0140 :> Common::Component {
            attribute :>> mass = 0.20 [kg];
            attribute :>> cost = 30.0;
            attribute range : Real = 140.0;
            port data : Common::DataPort;
        }
        part def Controller_0140 :> Common::Component {
            attribute :>> mass = 1.00 [kg];
            attribute :>> cost = 240.0;
            port supply : Common::PowerPort;
            part sensors : Sensor_0140[2];
            action smooth : Common::Process;
            action forward : Common::Process;
            succession first smooth then forward;
            exhibit state lifecycle : Common::Lifecycle;
        }
        requirement controllerMass_0140 : Common::MassLimit {
            subject component : Controller_0140;
            attribute :>> limit = 2.0 [kg];
        }
    }

    package Subsystem_0141 {
        part def Sensor_0141 :> Common::Component {
            attribute :>> mass = 0.21 [kg];
            attribute :>> cost = 31.0;
            attribute range : Real = 141.0;
            port data : Common::DataPort;
        }
        part def Controller_0141 :> Common::Component {
            attribute :>> mass = 1.10 [kg];
            attribute :>> cost = 241.0;
            port supply : Common::PowerPort;
            part sensors : Sensor_0141[2];
            action smooth : Common::Process;
            action forward : Common::Process;
            succession first smooth then forward;
            exhibit state lifecycle : Common::Lifecycle;
        }
        requirement controllerMass_0141 : Common::MassLimit {
            subject component : Controller_0141;
            attribute :>> limit = 2.0 [kg];
        }
    }

    package Subsystem_0142 {
        part def Sensor_0142 :> Common::Component {
            attribute :>> mass = 0.22 [kg];
            attribute :>> cost = 32.0;
            attribute range : Real = 142.0;
            port data : Common::DataPort;
        }
        part def Controller_0142 :> Common::Component {
            attribute :>> mass = 1.20 [kg];
            attribute :>> cost = 242.0;
            port supply : Common::PowerPort;
            part sensors : Sensor_0142[2];
            action smooth : Common::Process;
            action forward : Common::Process;
            succession first smooth then forward;
            exhibit state lifecycle : Common::Lifecycle;
        }
        requirement controllerMass_0142 : Common::MassLimit {
            subject component : Controller_0142;
            attribute :>> limit = 2.0 [kg];
        }
    }

    package Subsystem_0143 {
        part def Sensor_0143 :> Common::Component {
            attribute :>> mass = 0.23 [kg];
            attribute :>> cost = 33.0;
            attribute range : Real = 143.0;
            port data : Common::DataPort;
        }
        part def Controller_0143 :> Common::Component {
            attribute :>> mass = 1.30 [kg];
            attribute :>> cost = 243.0;
            port supply : Common::PowerPort;
            part sensors : Sensor_0143[2];
            action smooth : Common::Process;
            action forward : Common::Process;
            succession first smooth then forward;
            exhibit state lifecycle : Common::Lifecycle;
        }
        requirement controllerMass_0143 : Common::MassLimit {
            subject component : Controller_0143;
            attribute :>> limit = 2.0 [kg];
        }
    }

    package Subsystem_0144 {
        part def Sensor_0144 :> Common::Component {
            attribute :>> mass = 0.24 [kg];
            attribute :>> cost = 34.0;
            attribute range : Real = 144.0;
            port data : Common::DataPort;
        }
        part def Controller_0144 :> Common::Component {
            attribute :>> mass = 1.40 [kg];
            attribute :>> cost = 244.0;
            port supply : Common::PowerPort;
            part sensors : Sensor_0144[2];
            action smooth : Common::Process;
            action forward : Common::Process;
            succession first smooth then forward;
            exhibit state lifecycle : Common::Lifecycle;
        }
        requirement controllerMass_0144 : Common::MassLimit {
            subject component : Controller_0144;
            attribute :>> limit = 2.0 [kg];
        }
    }

    package Subsystem_0145 {
        part def Sensor_0145 :> Common::Component {
            attribute :>> mass = 0.20 [kg];
            attribute :>> cost = 35.0;
            attribute range : Real = 145.0;
            port data : Common::DataPort;
        }
        part def Controller_0145 :> Common::Component {
            attribute :>> mass = 1.50 [kg];
            attribute :>> cost = 245.0;
            port supply : Common::PowerPort;
            part sensors : Sensor_0145[2];
            action smooth : Common::Process;
            action forward : Common::Process;
            succession first smooth then forward;
            exhibit state lifecycle : Common::Lifecycle;
        }
        requirement controllerMass_0145 : Common::MassLimit {
            subject component : Controller_0145;
            attribute :>> limit = 2.0 [kg];
        }
    }

    package Subsystem_0146 {
        part def Sensor_0146 :> Common::Component {
            attribute :>> mass = 0.21 [kg];
            attribute :>> cost = 36.0;
            attribute range : Real = 146.0;
            port data : Common::DataPort;
        }
        part def Controller_0146 :> Common::Component {
            attribute :>> mass = 1.60 [kg];
            attribute :>> cost = 246.0;
            port supply : Common::PowerPort;
            part sensors : Sensor_0146[2];
            action smooth : Common::Process;
            action forward : Common::Process;
            succession first smooth then forward;
            exhibit state lifecycle : Common::Lifecycle;
        }
        requirement controllerMass_0146 : Common::MassLimit {
            subject component : Controller_0146;
            attribute :>> limit = 2.0 [kg];
        }
    }

    package Subsystem_0147 {
        part def Sensor_0147 :> Common::Component {
            attribute :>> mass = 0.22 [kg];
            attribute :>> cost = 37.0;
            attribute range : Real = 147.0;
            port data : Common::DataPort;
        }
        part def Controller_0147 :> Common::Component {
            attribute :>> mass = 1.00 [kg];
            attribute :>> cost = 247.0;
            port supply : Common::PowerPort;
            part sensors : Sensor_0147[2];
            action smooth : Common::Process;
            action forward : Common::Process;
            succession first smooth then forward;
            exhibit state lifecycle : Common::Lifecycle;
        }
        requirement controllerMass_0147 : Common::MassLimit {
            subject component : Controller_0147;
            attribute :>> limit = 2.0 [kg];
        }
    }

    package Subsystem_0148 {
        part def Sensor_0148 :> Common::Component {
            attribute :>> mass = 0.23 [kg];
            attribute :>> cost = 38.0;
            attribute range : Real = 148.0;
            port data : Common::DataPort;
        }
        part def Controller_0148 :> Common::Component {
            attribute :>> mass = 1.10 [kg];
            attribute :>> cost = 248.0;
            port supply : Common::PowerPort;
            part sensors : Sensor_0148[2];
            action smooth : Common::Process;
            action forward : Common::Process;
            succession first smooth then forward;
            exhibit state lifecycle : Common::Lifecycle;
        }
        requirement controllerMass_0148 : Common::MassLimit {
            subject component : Controller_0148;
            attribute :>> limit = 2.0 [kg];
        }
    }

    package Subsystem_0149 {
        part def Sensor_0149 :> Common::Component {
            attribute :>> mass = 0.24 [kg];
            attribute :>> cost = 39.0;
            attribute range : Real = 149.0;
            port data : Common::DataPort;
        }
        part def Controller_0149 :> Common::Component {
            attribute :>> mass = 1.20 [kg];
            attribute :>> cost = 249.0;
            port supply : Common::PowerPort;
            part sensors : Sensor_0149[2];
            action smooth : Common::Process;
            action forward : Common::Process;
            succession first smooth then forward;
            exhibit state lifecycle : Common::Lifecycle;
        }
        requirement controllerMass_0149 : Common::MassLimit {
            subject component : Controller_0149;
            attribute :>> limit = 2.0 [kg];
        }
    }

    package Subsystem_0150 {
        part def Sensor_0150 :> Common::Component {
            attribute :>> mass = 0.20 [kg];
            attribute :>> cost = 40.0;
            attribute range : Real = 100.0;
            port data : Common::DataPort;
        }
        part def Controller_0150 :> Common::Component {
            attribute :>> mass = 1.30 [kg];
            attribute :>> cost = 250.0;
            port supply : Common::PowerPort;
            part sensors : Sensor_0150[2];
            action smooth : Common::Process;
            action forward : Common::Process;
            succession first smooth then forward;
            exhibit state lifecycle : Common::Lifecycle;
        }
        requirement controllerMass_0150 : Common::MassLimit {
            subject component : Controller_0150;
            attribute :>> limit = 2.0 [kg];
        }
    }

    package Subsystem_0151 {
        part def Sensor_0151 :> Common::Component {
            attribute :>> mass = 0.21 [kg];
            attribute :>> cost = 41.0;
            attribute range : Real = 101.0;
            port data : Common::DataPort;
        }
        part def Controller_0151 :> Common::Component {
            attribute :>> mass = 1.40 [kg];
            attribute :>> cost = 251.0;
            port supply : Common::PowerPort;
            part sensors : Sensor_0151[2];
            action smooth : Common::Process;
            action forward : Common::Process;
            succession first smooth then forward;
            exhibit state lifecycle : Common::Lifecycle;
        }
        requirement controllerMass_0151 : Common::MassLimit {
            subject component : Controller_0151;
            attribute :>> limit = 2.0 [kg];
        }
    }

    package Subsystem_0152 {
        part def Sensor_0152 :> Common::Component {
            attribute :>> mass = 0.22 [kg];
            attribute :>> cost = 42.0;
            attribute range : Real = 102.0;
            port data : Common::DataPort;
        }
        part def Controller_0152 :> Common::Component {
            attribute :>> mass = 1.50 [kg];
            attribute :>> cost = 252.0;
            port supply : Common::PowerPort;
            part sensors : Sensor_0152[2];
            action smooth : Common::Process;
            action forward : Common::Process;
            succession first smooth then forward;
            exhibit state lifecycle : Common::Lifecycle;
        }
        requirement controllerMass_0152 : Common::MassLimit {
            subject component : Controller_0152;
            attribute :>> limit = 2.0 [kg];
        }
    }

    package Subsystem_0153 {
        part def Sensor_0153 :> Common::Component {
            attribute :>> mass = 0.23 [kg];
            attribute :>> cost = 43.0;
            attribute range : Real = 103.0;
            port data : Common::DataPort;
        }
        part def Controller_0153 :> Common::Component {
            attribute :>> mass = 1.60 [kg];
            attribute :>> cost = 253.0;
            port supply : Common::PowerPort;
            part sensors : Sensor_0153[2];
            action smooth : Common::Process;
            action forward : Common::Process;
            succession first smooth then forward;
            exhibit state lifecycle : Common::Lifecycle;
        }
        requirement controllerMass_0153 : Common::MassLimit {
            subject component : Controller_0153;
            attribute :>> limit = 2.0 [kg];
        }
    }

    package Subsystem_0154 {
        part def Sensor_0154 :> Common::Component {
            attribute :>> mass = 0.24 [kg];
            attribute :>> cost = 44.0;
            attribute range : Real = 104.0;
            port data : Common::DataPort;
        }
        part def Controller_0154 :> Common::Component {
            attribute :>> mass = 1.00 [kg];
            attribute :>> cost = 254.0;
            port supply : Common::PowerPort;
            part sensors : Sensor_0154[2];
            action smooth : Common::Process;
            action forward : Common::Process;
            succession first smooth then forward;
            exhibit state lifecycle : Common::Lifecycle;
        }
        requirement controllerMass_0154 : Common::MassLimit {
            subject component : Controller_0154;
            attribute :>> limit = 2.0 [kg];
        }
    }

    package Subsystem_0155 {
        part def Sensor_0155 :> Common::Component {
            attribute :>> mass = 0.20 [kg];
            attribute :>> cost = 45.0;
            attribute range : Real = 105.0;
            port data : Common::DataPort;
        }
        part def Controller_0155 :> Common::Component {
            attribute :>> mass = 1.10 [kg];
            attribute :>> cost = 255.0;
            port supply : Common::PowerPort;
            part sensors : Sensor_0155[2];
            action smooth : Common::Process;
            action forward : Common::Process;
            succession first smooth then forward;
            exhibit state lifecycle : Common::Lifecycle;
        }
        requirement controllerMass_0155 : Common::MassLimit {
            subject component : Controller_0155;
            attribute :>> limit = 2.0 [kg];
        }
    }

    package Subsystem_0156 {
        part def Sensor_0156 :> Common::Component {
            attribute :>> mass = 0.21 [kg];
            attribute :>> cost = 46.0;
            attribute range : Real = 106.0;
            port data : Common::DataPort;
        }
        part def Controller_0156 :> Common::Component {
            attribute :>> mass = 1.20 [kg];
            attribute :>> cost = 256.0;
            port supply : Common::PowerPort;
            part sensors : Sensor_0156[2];
            action smooth : Common::Process;
            action forward : Common::Process;
            succession first smooth then forward;
            exhibit state lifecycle : Common::Lifecycle;
        }
        requirement controllerMass_0156 : Common::MassLimit {
            subject component : Controller_0156;
            attribute :>> limit = 2.0 [kg];
        }
    }

    package Subsystem_0157 {
        part def Sensor_0157 :> Common::Component {
            attribute :>> mass = 0.22 [kg];
            attribute :>> cost = 47.0;
            attribute range : Real = 107.0;
            port data : Common::DataPort;
        }
        part def Controller_0157 :> Common::Component {
            attribute :>> mass = 1.30 [kg];
            attribute :>> cost = 257.0;
            port supply : Common::PowerPort;
            part sensors : Sensor_0157[2];
            action smooth : Common::Process;
            action forward : Common::Process;
            succession first smooth then forward;
            exhibit state lifecycle : Common::Lifecycle;
        }
        requirement controllerMass_0157 : Common::MassLimit {
            subject component : Controller_0157;
            attribute :>> limit = 2.0 [kg];
        }
    }

    package Subsystem_0158 {
        part def Sensor_0158 :> Common::Component {
            attribute :>> mass = 0.23 [kg];
            attribute :>> cost = 48.0;
            attribute range : Real = 108.0;
            port data : Common::DataPort;
        }
        part def Controller_0158 :> Common::Component {
            attribute :>> mass = 1.40 [kg];
            attribute :>> cost = 258.0;
            port supply : Common::PowerPort;
            part sensors : Sensor_0158[2];
            action smooth : Common::Process;
            action forward : Common::Process;
            succession first smooth then forward;
            exhibit state lifecycle : Common::Lifecycle;
        }
        requirement controllerMass_0158 : Common::MassLimit {
            subject component : Controller_0158;
            attribute :>> limit = 2.0 [kg];
        }
    }

    package Subsystem_0159 {
        part def Sensor_0159 :> Common::Component {
            attribute :>> mass = 0.24 [kg];
            attribute :>> cost = 49.0;
            attribute range : Real = 109.0;
            port data : Common::DataPort;
        }
        part def Controller_0159 :> Common::Component {
            attribute :>> mass = 1.50 [kg];
            attribute :>> cost = 259.0;
            port supply : Common::PowerPort;
            part sensors : Sensor_0159[2];
            action smooth : Common::Process;
            action forward : Common::Process;
            succession first smooth then forward;
            exhibit state lifecycle : Common::Lifecycle;
        }
        requirement controllerMass_0159 : Common::MassLimit {
            subject component : Controller_0159;
            attribute :>> limit = 2.0 [kg];
        }
    }

    package Subsystem_0160 {
        part def Sensor_0160 :> Common::Component {
            attribute :>> mass = 0.20 [kg];
            attribute :>> cost = 30.0;
            attribute range : Real = 110.0;
            port data : Common::DataPort;
        }
        part def Controller_0160 :> Common::Component {
            attribute :>> mass = 1.60 [kg];
            attribute :>> cost = 260.0;
            port supply : Common::PowerPort;
            part sensors : Sensor_0160[2];
            action smooth : Common::Process;
            action forward : Common::Process;
            succession first smooth then forward;
            exhibit state lifecycle : Common::Lifecycle;
        }
        requirement controllerMass_0160 : Common::MassLimit {
            subject component : Controller_0160;
            attribute :>> limit = 2.0 [kg];
        }
    }

    package Subsystem_0161 {
        part def Sensor_0161 :> Common::Component {
            attribute :>> mass = 0.21 [kg];
            attribute :>> cost = 31.0;
            attribute range : Real = 111.0;
            port data : Common::DataPort;
        }
        part def Controller_0161 :> Common::Component {
            attribute :>> mass = 1.00 [kg];
            attribute :>> cost = 261.0;
            port supply : Common::PowerPort;
            part sensors : Sensor_0161[2];
            action smooth : Common::Process;
            action forward : Common::Process;
            succession first smooth then forward;
            exhibit state lifecycle : Common::Lifecycle;
        }
        requirement controllerMass_0161 : Common::MassLimit {
            subject component : Controller_0161;
            attribute :>> limit = 2.0 [kg];
        }
    }

    package Subsystem_0162 {
        part def Sensor_0162 :> Common::Component {
            attribute :>> mass = 0.22 [kg];
            attribute :>> cost = 32.0;
            attribute range : Real = 112.0;
            port data : Common::DataPort;
        }
        part def Controller_0162 :> Common::Component {
            attribute :>> mass = 1.10 [kg];
            attribute :>> cost = 262.0;
            port supply : Common::PowerPort;
            part sensors : Sensor_0162[2];
            action smooth : Common::Process;
            action forward : Common::Process;
            succession first smooth then forward;
            exhibit state lifecycle : Common::Lifecycle;
        }
        requirement controllerMass_0162 : Common::MassLimit {
            subject component : Controller_0162;
            attribute :>> limit = 2.0 [kg];
        }
    }

    package Subsystem_0163 {
        part def Sensor_0163 :> Common::Component {
            attribute :>> mass = 0.23 [kg];
            attribute :>> cost = 33.0;
            attribute range : Real = 113.0;
            port data : Common::DataPort;
        }
        part def Controller_0163 :> Common::Component {
            attribute :>> mass = 1.20 [kg];
            attribute :>> cost = 263.0;
            port supply : Common::PowerPort;
            part sensors : Sensor_0163[2];
            action smooth : Common::Process;
            action forward : Common::Process;
            succession first smooth then forward;
            exhibit state lifecycle : Common::Lifecycle;
        }
        requirement controllerMass_0163 : Common::MassLimit {
            subject component : Controller_0163;
            attribute :>> limit = 2.0 [kg];
        }
    }

    package Subsystem_0164 {
        part def Sensor_0164 :> Common::Component {
            attribute :>> mass = 0.24 [kg];
            attribute :>> cost = 34.0;
            attribute range : Real = 114.0;
            port data : Common::DataPort;
        }
        part def Controller_0164 :> Common::Component {
            attribute :>> mass = 1.30 [kg];
            attribute :>> cost = 264.0;
            port supply : Common::PowerPort;
            part sensors : Sensor_0164[2];
            action smooth : Common::Process;
            action forward : Common::Process;
            succession first smooth then forward;
            exhibit state lifecycle : Common::Lifecycle;
        }
        requirement controllerMass_0164 : Common::MassLimit {
            subject component : Controller_0164;
            attribute :>> limit = 2.0 [kg];
        }
    }

    package Subsystem_0165 {
        part def Sensor_0165 :> Common::Component {
            attribute :>> mass = 0.20 [kg];
            attribute :>> cost = 35.0;
            attribute range : Real = 115.0;
            port data : Common::DataPort;
        }
        part def Controller_0165 :> Common::Component {
            attribute :>> mass = 1.40 [kg];
            attribute :>> cost = 265.0;
            port supply : Common::PowerPort;
            part sensors : Sensor_0165[2];
            action smooth : Common::Process;
            action forward : Common::Process;
            succession first smooth then forward;
            exhibit state lifecycle : Common::Lifecycle;
        }
        requirement controllerMass_0165 : Common::MassLimit {
            subject component : Controller_0165;
            attribute :>> limit = 2.0 [kg];
        }
    }

    package Subsystem_0166 {
        part def Sensor_0166 :> Common::Component {
            attribute :>> mass = 0.21 [kg];
            attribute :>> cost = 36.0;
            attribute range : Real = 116.0;
            port data : Common::DataPort;
        }
        part def Controller_0166 :> Common::Component {
            attribute :>> mass = 1.50 [kg];
            attribute :>> cost = 266.0;
            port supply : Common::PowerPort;
            part sensors : Sensor_0166[2];
            action smooth : Common::Process;
            action forward : Common::Process;
            succession first smooth then forward;
            exhibit state lifecycle : Common::Lifecycle;
        }
        requirement controllerMass_0166 : Common::MassLimit {
            subject component : Controller_0166;
            attribute :>> limit = 2.0 [kg];
        }
    }

    package Subsystem_0167 {
        part def Sensor_0167 :> Common::Component {
            attribute :>> mass = 0.22 [kg];
            attribute :>> cost = 37.0;
            attribute range : Real = 117.0;
            port data : Common::DataPort;
        }
        part def Controller_0167 :> Common::Component {
            attribute :>> mass = 1.60 [kg];
            attribute :>> cost = 267.0;
            port supply : Common::PowerPort;
            part sensors : Sensor_0167[2];
            action smooth : Common::Process;
            action forward : Common::Process;
            succession first smooth then forward;
            exhibit state lifecycle : Common::Lifecycle;
        }
        requirement controllerMass_0167 : Common::MassLimit {
            subject component : Controller_0167;
            attribute :>> limit = 2.0 [kg];
        }
    }

    package Subsystem_0168 {
        part def Sensor_0168 :> Common::Component {
            attribute :>> mass = 0.23 [kg];
            attribute :>> cost = 38.0;
            attribute range : Real = 118.0;
            port data : Common::DataPort;
        }
        part def Controller_0168 :> Common::Component {
            attribute :>> mass = 1.00 [kg];
            attribute :>> cost = 268.0;
            port supply : Common::PowerPort;
            part sensors : Sensor_0168[2];
            action smooth : Common::Process;
            action forward : Common::Process;
            succession first smooth then forward;
            exhibit state lifecycle : Common::Lifecycle;
        }
        requirement controllerMass_0168 : Common::MassLimit {
            subject component : Controller_0168;
            attribute :>> limit = 2.0 [kg];
        }
    }

    package Subsystem_0169 {
        part def Sensor_0169 :> Common::Component {
            attribute :>> mass = 0.24 [kg];
            attribute :>> cost = 39.0;
            attribute range : Real = 119.0;
            port data : Common::DataPort;
        }
        part def Controller_0169 :> Common::Component {
            attribute :>> mass = 1.10 [kg];
            attribute :>> cost = 269.0;
            port supply : Common::PowerPort;
            part sensors : Sensor_0169[2];
            action smooth : Common::Process;
            action forward : Common::Process;
            succession first smooth then forward;
            exhibit state lifecycle : Common::Lifecycle;
        }
        requirement controllerMass_0169 : Common::MassLimit {
            subject component : Controller_0169;
            attribute :>> limit = 2.0 [kg];
        }
    }

    package Subsystem_0170 {
        part def Sensor_0170 :> Common::Component {
            attribute :>> mass = 0.20 [kg];
            attribute :>> cost = 40.0;
            attribute range : Real = 120.0;
            port data : Common::DataPort;
        }
        part def Controller_0170 :> Common::Component {
            attribute :>> mass = 1.20 [kg];
            attribute :>> cost = 270.0;
            port supply : Common::PowerPort;
            part sensors : Sensor_0170[2];
            action smooth : Common::Process;
            action forward : Common::Process;
            succession first smooth then forward;
            exhibit state lifecycle : Common::Lifecycle;
        }
        requirement controllerMass_0170 : Common::MassLimit {
            subject component : Controller_0170;
            attribute :>> limit = 2.0 [kg];
        }
    }

    package Subsystem_0171 {
        part def Sensor_0171 :> Common::Component {
            attribute :>> mass = 0.21 [kg];
            attribute :>> cost = 41.0;
            attribute range : Real = 121.0;
            port data : Common::DataPort;
        }
        part def Controller_0171 :> Common::Component {
            attribute :>> mass = 1.30 [kg];
            attribute :>> cost = 271.0;
            port supply : Common::PowerPort;
            part sensors : Sensor_0171[2];
            action smooth : Common::Process;
            action forward : Common::Process;
            succession first smooth then forward;
            exhibit state lifecycle : Common::Lifecycle;
        }
        requirement controllerMass_0171 : Common::MassLimit {
            subject component : Controller_0171;
            attribute :>> limit = 2.0 [kg];
        }
    }

    package Subsystem_0172 {
        part def Sensor_0172 :> Common::Component {
            attribute :>> mass = 0.22 [kg];
            attribute :>> cost = 42.0;
            attribute range : Real = 122.0;
            port data : Common::DataPort;
        }
        part def Controller_0172 :> Common::Component {
            attribute :>> mass = 1.40 [kg];
            attribute :>> cost = 272.0;
            port supply : Common::PowerPort;
            part sensors : Sensor_0172[2];
            action smooth : Common::Process;
            action forward : Common::Process;
            succession first smooth then forward;
            exhibit state lifecycle : Common::Lifecycle;
        }
        requirement controllerMass_0172 : Common::MassLimit {
            subject component : Controller_0172;
            attribute :>> limit = 2.0 [kg];
        }
    }

    package Subsystem_0173 {
        part def Sensor_0173 :> Common::Component {
            attribute :>> mass = 0.23 [kg];
            attribute :>> cost = 43.0;
            attribute range : Real = 123.0;
            port data : Common::DataPort;
        }
        part def Controller_0173 :> Common::Component {
            attribute :>> mass = 1.50 [kg];
            attribute :>> cost = 273.0;
            port supply : Common::PowerPort;
            part sensors : Sensor_0173[2];
            action smooth : Common::Process;
            action forward : Common::Process;
            succession first smooth then forward;
            exhibit state lifecycle : Common::Lifecycle;
        }
        requirement controllerMass_0173 : Common::MassLimit {
            subject component : Controller_0173;
            attribute :>> limit = 2.0 [kg];
        }
    }

    package Subsystem_0174 {
        part def Sensor_0174 :> Common::Component {
            attribute :>> mass = 0.24 [kg];
            attribute :>> cost = 44.0;
            attribute range : Real = 124.0;
            port data : Common::DataPort;
        }
        part def Controller_0174 :> Common::Component {
            attribute :>> mass = 1.60 [kg];
            attribute :>> cost = 274.0;
            port supply : Common::PowerPort;
            part sensors : Sensor_0174[2];
            action smooth : Common::Process;
            action forward : Common::Process;
            succession first smooth then forward;
            exhibit state lifecycle : Common::Lifecycle;
        }
        requirement controllerMass_0174 : Common::MassLimit {
            subject component : Controller_0174;
            attribute :>> limit = 2.0 [kg];
        }
    }

    package Subsystem_0175 {
        part def Sensor_0175 :> Common::Component {
            attribute :>> mass = 0.20 [kg];
            attribute :>> cost = 45.0;
            attribute range : Real = 125.0;
            port data : Common::DataPort;
        }
        part def Controller_0175 :> Common::Component {
            attribute :>> mass = 1.00 [kg];
            attribute :>> cost = 275.0;
            port supply : Common::PowerPort;
            part sensors : Sensor_0175[2];
            action smooth : Common::Process;
            action forward : Common::Process;
            succession first smooth then forward;
            exhibit state lifecycle : Common::Lifecycle;
        }
        requirement controllerMass_0175 : Common::MassLimit {
            subject component : Controller_0175;
            attribute :>> limit = 2.0 [kg];
        }
    }

    package Subsystem_0176 {
        part def Sensor_0176 :> Common::Component {
            attribute :>> mass = 0.21 [kg];
            attribute :>> cost = 46.0;
            attribute range : Real = 126.0;
            port data : Common::DataPort;
        }
        part def Controller_0176 :> Common::Component {
            attribute :>> mass = 1.10 [kg];
            attribute :>> cost = 276.0;
            port supply : Common::PowerPort;
            part sensors : Sensor_0176[2];
            action smooth : Common::Process;
            action forward : Common::Process;
            succession first smooth then forward;
            exhibit state lifecycle : Common::Lifecycle;
        }
        requirement controllerMass_0176 : Common::MassLimit {
            subject component : Controller_0176;
            attribute :>> limit = 2.0 [kg];
        }
    }

    package Subsystem_0177 {
        part def Sensor_0177 :> Common::Component {
            attribute :>> mass = 0.22 [kg];
            attribute :>> cost = 47.0;
            attribute range : Real = 127.0;
            port data : Common::DataPort;
        }
        part def Controller_0177 :> Common::Component {
            attribute :>> mass = 1.20 [kg];
            attribute :>> cost = 277.0;
            port supply : Common::PowerPort;
            part sensors : Sensor_0177[2];
            action smooth : Common::Process;
            action forward : Common::Process;
            succession first smooth then forward;
            exhibit state lifecycle : Common::Lifecycle;
        }
        requirement controllerMass_0177 : Common::MassLimit {
            subject component : Controller_0177;
            attribute :>> limit = 2.0 [kg];
        }
    }

    package Subsystem_0178 {
        part def Sensor_0178 :> Common::Component {
            attribute :>> mass = 0.23 [kg];
            attribute :>> cost = 48.0;
            attribute range : Real = 128.0;
            port data : Common::DataPort;
        }
        part def Controller_0178 :> Common::Component {
            attribute :>> mass = 1.30 [kg];
            attribute :>> cost = 278.0;
            port supply : Common::PowerPort;
            part sensors : Sensor_0178[2];
            action smooth : Common::Process;
            action forward : Common::Process;
            succession first smooth then forward;
            exhibit state lifecycle : Common::Lifecycle;
        }
        requirement controllerMass_0178 : Common::MassLimit {
            subject component : Controller_0178;
            attribute :>> limit = 2.0 [kg];
        }
    }

    package Subsystem_0179 {
        part def Sensor_0179 :> Common::Component {
            attribute :>> mass = 0.24 [kg];
            attribute :>> cost = 49.0;
            attribute range : Real = 129.0;
            port data : Common::DataPort;
        }
        part def Controller_0179 :> Common::Component {
            attribute :>> mass = 1.40 [kg];
            attribute :>> cost = 279.0;
            port supply : Common::PowerPort;
            part sensors : Sensor_0179[2];
            action smooth : Common::Process;
            action forward : Common::Process;
            succession first smooth then forward;
            exhibit state lifecycle : Common::Lifecycle;
        }
        requirement controllerMass_0179 : Common::MassLimit {
            subject component : Controller_0179;
            attribute :>> limit = 2.0 [kg];
        }
    }

    package Subsystem_0180 {
        part def Sensor_0180 :> Common::Component {
            attribute :>> mass = 0.20 [kg];
            attribute :>> cost = 30.0;
            attribute range : Real = 130.0;
            port data : Common::DataPort;
        }
        part def Controller_0180 :> Common::Component {
            attribute :>> mass = 1.50 [kg];
            attribute :>> cost = 280.0;
            port supply : Common::PowerPort;
            part sensors : Sensor_0180[2];
            action smooth : Common::Process;
            action forward : Common::Process;
            succession first smooth then forward;
            exhibit state lifecycle : Common::Lifecycle;
        }
        requirement controllerMass_0180 : Common::MassLimit {
            subject component : Controller_0180;
            attribute :>> limit = 2.0 [kg];
        }
    }

    package Subsystem_0181 {
        part def Sensor_0181 :> Common::Component {
            attribute :>> mass = 0.21 [kg];
            attribute :>> cost = 31.0;
            attribute range : Real = 131.0;
            port data : Common::DataPort;
        }
        part def Controller_0181 :> Common::Component {
            attribute :>> mass = 1.60 [kg];
            attribute :>> cost = 281.0;
            port supply : Common::PowerPort;
            part sensors : Sensor_0181[2];
            action smooth : Common::Process;
            action forward : Common::Process;
            succession first smooth then forward;
            exhibit state lifecycle : Common::Lifecycle;
        }
        requirement controllerMass_0181 : Common::MassLimit {
            subject component : Controller_0181;
            attribute :>> limit = 2.0 [kg];
        }
    }

    package Subsystem_0182 {
        part def Sensor_0182 :> Common::Component {
            attribute :>> mass = 0.22 [kg];
            attribute :>> cost = 32.0;
            attribute range : Real = 132.0;
            port data : Common::DataPort;
        }
        part def Controller_0182 :> Common::Component {
            attribute :>> mass = 1.00 [kg];
            attribute :>> cost = 282.0;
            port supply : Common::PowerPort;
            part sensors : Sensor_0182[2];
            action smooth : Common::Process;
            action forward : Common::Process;
            succession first smooth then forward;
            exhibit state lifecycle : Common::Lifecycle;
        }
        requirement controllerMass_0182 : Common::MassLimit {
            subject component : Controller_0182;
            attribute :>> limit = 2.0 [kg];
        }
    }

    package Subsystem_0183 {
        part def Sensor_0183 :> Common::Component {
            attribute :>> mass = 0.23 [kg];
            attribute :>> cost = 33.0;
            attribute range : Real = 133.0;
            port data : Common::DataPort;
        }
        part def Controller_0183 :> Common::Component {
            attribute :>> mass = 1.10 [kg];
            attribute :>> cost = 283.0;
            port supply : Common::PowerPort;
            part sensors : Sensor_0183[2];
            action smooth : Common::Process;
            action forward : Common::Process;
            succession first smooth then forward;
            exhibit state lifecycle : Common::Lifecycle;
        }
        requirement controllerMass_0183 : Common::MassLimit {
            subject component : Controller_0183;
            attribute :>> limit = 2.0 [kg];
        }
    }

    package Subsystem_0184 {
        part def Sensor_0184 :> Common::Component {
            attribute :>> mass = 0.24 [kg];
            attribute :>> cost = 34.0;
            attribute range : Real = 134.0;
            port data : Common::DataPort;
        }
        part def Controller_0184 :> Common::Component {
            attribute :>> mass = 1.20 [kg];
            attribute :>> cost = 284.0;
            port supply : Common::PowerPort;
            part sensors : Sensor_0184[2];
            action smooth : Common::Process;
            action forward : Common::Process;
            succession first smooth then forward;
            exhibit state lifecycle : Common::Lifecycle;
        }
        requirement controllerMass_0184 : Common::MassLimit {
            subject component : Controller_0184;
            attribute :>> limit = 2.0 [kg];
        }
    }

    package Subsystem_0185 {
        part def Sensor_0185 :> Common::Component {
            attribute :>> mass = 0.20 [kg];
            attribute :>> cost = 35.0;
            attribute range : Real = 135.0;
            port data : Common::DataPort;
        }
        part def Controller_0185 :> Common::Component {
            attribute :>> mass = 1.30 [kg];
            attribute :>> cost = 285.0;
            port supply : Common::PowerPort;
            part sensors : Sensor_0185[2];
            action smooth : Common::Process;
            action forward : Common::Process;
            succession first smooth then forward;
            exhibit state lifecycle : Common::Lifecycle;
        }
        requirement controllerMass_0185 : Common::MassLimit {
            subject component : Controller_0185;
            attribute :>> limit = 2.0 [kg];
        }
    }

    package Subsystem_0186 {
        part def Sensor_0186 :> Common::Component {
            attribute :>> mass = 0.21 [kg];
            attribute :>> cost = 36.0;
            attribute range : Real = 136.0;
            port data : Common::DataPort;
        }
        part def Controller_0186 :> Common::Component {
            attribute :>> mass = 1.40 [kg];
            attribute :>> cost = 286.0;
            port supply : Common::PowerPort;
            part sensors : Sensor_0186[2];
            action smooth : Common::Process;
            action forward : Common::Process;
            succession first smooth then forward;
            exhibit state lifecycle : Common::Lifecycle;
        }
        requirement controllerMass_0186 : Common::MassLimit {
            subject component : Controller_0186;
            attribute :>> limit = 2.0 [kg];
        }
    }

    package Subsystem_0187 {
        part def Sensor_0187 :> Common::Component {
            attribute :>> mass = 0.22 [kg];
            attribute :>> cost = 37.0;
            attribute range : Real = 137.0;
            port data : Common::DataPort;
        }
        part def Controller_0187 :> Common::Component {
            attribute :>> mass = 1.50 [kg];
            attribute :>> cost = 287.0;
            port supply : Common::PowerPort;
            part sensors : Sensor_0187[2];
            action smooth : Common::Process;
            action forward : Common::Process;
            succession first smooth then forward;
            exhibit state lifecycle : Common::Lifecycle;
        }
        requirement controllerMass_0187 : Common::MassLimit {
            subject component : Controller_0187;
            attribute :>> limit = 2.0 [kg];
        }
    }

    package Subsystem_0188 {
        part def Sensor_0188 :> Common::Component {
            attribute :>> mass = 0.23 [kg];
            attribute :>> cost = 38.0;
            attribute range : Real = 138.0;
            port data : Common::DataPort;
        }
        part def Controller_0188 :> Common::Component {
            attribute :>> mass = 1.60 [kg];
            attribute :>> cost = 288.0;
            port supply : Common::PowerPort;
            part sensors : Sensor_0188[2];
            action smooth : Common::Process;
            action forward : Common::Process;
            succession first smooth then forward;
            exhibit state lifecycle : Common::Lifecycle;
        }
        requirement controllerMass_0188 : Common::MassLimit {
            subject component : Controller_0188;
            attribute :>> limit = 2.0 [kg];
        }
    }

    package Subsystem_0189 {
        part def Sensor_0189 :> Common::Component {
            attribute :>> mass = 0.24 [kg];
            attribute :>> cost = 39.0;
            attribute range : Real = 139.0;
            port data : Common::DataPort;
        }
        part def Controller_0189 :> Common::Component {
            attribute :>> mass = 1.00 [kg];
            attribute :>> cost = 289.0;
            port supply : Common::PowerPort;
            part sensors : Sensor_0189[2];
            action smooth : Common::Process;
            action forward : Common::Process;
            succession first smooth then forward;
            exhibit state lifecycle : Common::Lifecycle;
        }
        requirement controllerMass_0189 : Common::MassLimit {
            subject component : Controller_0189;
            attribute :>> limit = 2.0 [kg];
        }
    }

    package Subsystem_0190 {
        part def Sensor_0190 :> Common::Component {
            attribute :>> mass = 0.20 [kg];
            attribute :>> cost = 40.0;
            attribute range : Real = 140.0;
            port data : Common::DataPort;
        }
        part def Controller_0190 :> Common::Component {
            attribute :>> mass = 1.10 [kg];
            attribute :>> cost = 290.0;
            port supply : Common::PowerPort;
            part sensors : Sensor_0190[2];
            action smooth : Common::Process;
            action forward : Common::Process;
            succession first smooth then forward;
            exhibit state lifecycle : Common::Lifecycle;
        }
        requirement controllerMass_0190 : Common::MassLimit {
            subject component : Controller_0190;
            attribute :>> limit = 2.0 [kg];
        }
    }

    package Subsystem_0191 {
        part def Sensor_0191 :> Common::Component {
            attribute :>> mass = 0.21 [kg];
            attribute :>> cost = 41.0;
            attribute range : Real = 141.0;
            port data : Common::DataPort;
        }
        part def Controller_0191 :> Common::Component {
            attribute :>> mass = 1.20 [kg];
            attribute :>> cost = 291.0;
            port supply : Common::PowerPort;
            part sensors : Sensor_0191[2];
            action smooth : Common::Process;
            action forward : Common::Process;
            succession first smooth then forward;
            exhibit state lifecycle : Common::Lifecycle;
        }
        requirement controllerMass_0191 : Common::MassLimit {
            subject component : Controller_0191;
            attribute :>> limit = 2.0 [kg];
        }
    }

    package Subsystem_0192 {
        part def Sensor_0192 :> Common::Component {
            attribute :>> mass = 0.22 [kg];
            attribute :>> cost = 42.0;
            attribute range : Real = 142.0;
            port data : Common::DataPort;
        }
        part def Controller_0192 :> Common::Component {
            attribute :>> mass = 1.30 [kg];
            attribute :>> cost = 292.0;
            port supply : Common::PowerPort;
            part sensors : Sensor_0192[2];
            action smooth : Common::Process;
            action forward : Common::Process;
            succession first smooth then forward;
            exhibit state lifecycle : Common::Lifecycle;
        }
        requirement controllerMass_0192 : Common::MassLimit {
            subject component : Controller_0192;
            attribute :>> limit = 2.0 [kg];
        }
    }

    package Subsystem_0193 {
        part def Sensor_0193 :> Common::Component {
            attribute :>> mass = 0.23 [kg];
            attribute :>> cost = 43.0;
            attribute range : Real = 143.0;
            port data : Common::DataPort;
        }
        part def Controller_0193 :> Common::Component {
            attribute :>> mass = 1.40 [kg];
            attribute :>> cost = 293.0;
            port supply : Common::PowerPort;
            part sensors : Sensor_0193[2];
            action smooth : Common::Process;
            action forward : Common::Process;
            succession first smooth then forward;
            exhibit state lifecycle : Common::Lifecycle;
        }
        requirement controllerMass_0193 : Common::MassLimit {
            subject component : Controller_0193;
            attribute :>> limit = 2.0 [kg];
        }
    }

    package Subsystem_0194 {
        part def Sensor_0194 :> Common::Component {
            attribute :>> mass = 0.24 [kg];
            attribute :>> cost = 44.0;
            attribute range : Real = 144.0;
            port data : Common::DataPort;
        }
        part def Controller_0194 :> Common::Component {
            attribute :>> mass = 1.50 [kg];
            attribute :>> cost = 294.0;
            port supply : Common::PowerPort;
            part sensors : Sensor_0194[2];
            action smooth : Common::Process;
            action forward : Common::Process;
            succession first smooth then forward;
            exhibit state lifecycle : Common::Lifecycle;
        }
        requirement controllerMass_0194 : Common::MassLimit {
            subject component : Controller_0194;
            attribute :>> limit = 2.0 [kg];
        }
    }

    package Subsystem_0195 {
        part def Sensor_0195 :> Common::Component {
            attribute :>> mass = 0.20 [kg];
            attribute :>> cost = 45.0;
            attribute range : Real = 145.0;
            port data : Common::DataPort;
        }
        part def Controller_0195 :> Common::Component {
            attribute :>> mass = 1.60 [kg];
            attribute :>> cost = 295.0;
            port supply : Common::PowerPort;
            part sensors : Sensor_0195[2];
            action smooth : Common::Process;
            action forward : Common::Process;
            succession first smooth then forward;
            exhibit state lifecycle : Common::Lifecycle;
        }
        requirement controllerMass_0195 : Common::MassLimit {
            subject component : Controller_0195;
            attribute :>> limit = 2.0 [kg];
        }
    }

    package Subsystem_0196 {
        part def Sensor_0196 :> Common::Component {
            attribute :>> mass = 0.21 [kg];
            attribute :>> cost = 46.0;
            attribute range : Real = 146.0;
            port data : Common::DataPort;
        }
        part def Controller_0196 :> Common::Component {
            attribute :>> mass = 1.00 [kg];
            attribute :>> cost = 296.0;
            port supply : Common::PowerPort;
            part sensors : Sensor_0196[2];
            action smooth : Common::Process;
            action forward : Common::Process;
            succession first smooth then forward;
            exhibit state lifecycle : Common::Lifecycle;
        }
        requirement controllerMass_0196 : Common::MassLimit {
            subject component : Controller_0196;
            attribute :>> limit = 2.0 [kg];
        }
    }

    package Subsystem_0197 {
        part def Sensor_0197 :> Common::Component {
            attribute :>> mass = 0.22 [kg];
            attribute :>> cost = 47.0;
            attribute range : Real = 147.0;
            port data : Common::DataPort;
        }
        part def Controller_0197 :> Common::Component {
            attribute :>> mass = 1.10 [kg];
            attribute :>> cost = 297.0;
            port supply : Common::PowerPort;
            part sensors : Sensor_0197[2];
            action smooth : Common::Process;
            action forward : Common::Process;
            succession first smooth then forward;
            exhibit state lifecycle : Common::Lifecycle;
        }
        requirement controllerMass_0197 : Common::MassLimit {
            subject component : Controller_0197;
            attribute :>> limit = 2.0 [kg];
        }
    }

    package Subsystem_0198 {
        part def Sensor_0198 :> Common::Component {
            attribute :>> mass = 0.23 [kg];
            attribute :>> cost = 48.0;
            attribute range : Real = 148.0;
            port data : Common::DataPort;
        }
        part def Controller_0198 :> Common::Component {
            attribute :>> mass = 1.20 [kg];
            attribute :>> cost = 298.0;
            port supply : Common::PowerPort;
            part sensors : Sensor_0198[2];
            action smooth : Common::Process;
            action forward : Common::Process;
            succession first smooth then forward;
            exhibit state lifecycle : Common::Lifecycle;
        }
        requirement controllerMass_0198 : Common::MassLimit {
            subject component : Controller_0198;
            attribute :>> limit = 2.0 [kg];
        }
    }

    package Subsystem_0199 {
        part def Sensor_0199 :> Common::Component {
            attribute :>> mass = 0.24 [kg];
            attribute :>> cost = 49.0;
            attribute range : Real = 149.0;
            port data : Common::DataPort;
        }
        part def Controller_0199 :> Common::Component {
            attribute :>> mass = 1.30 [kg];
            attribute :>> cost = 299.0;
            port supply : Common::PowerPort;
            part sensors : Sensor_0199[2];
            action smooth : Common::Process;
            action forward : Common::Process;
            succession first smooth then forward;
            exhibit state lifecycle : Common::Lifecycle;
        }
        requirement controllerMass_0199 : Common::MassLimit {
            subject component : Controller_0199;
            attribute :>> limit = 2.0 [kg];
        }
    }

    package Subsystem_0200 {
        part def Sensor_0200 :> Common::Component {
            attribute :>> mass = 0.20 [kg];
            attribute :>> cost = 30.0;
            attribute range : Real = 100.0;
            port data : Common::DataPort;
        }
        part def Controller_0200 :> Common::Component {
            attribute :>> mass = 1.40 [kg];
            attribute :>> cost = 200.0;
            port supply : Common::PowerPort;
            part sensors : Sensor_0200[2];
            action smooth : Common::Process;
            action forward : Common::Process;
            succession first smooth then forward;
            exhibit state lifecycle : Common::Lifecycle;
        }
        requirement controllerMass_0200 : Common::MassLimit {
            subject component : Controller_0200;
            attribute :>> limit = 2.0 [kg];
        }
    }

    package Subsystem_0201 {
        part def Sensor_0201 :> Common::Component {
            attribute :>> mass = 0.21 [kg];
            attribute :>> cost = 31.0;
            attribute range : Real = 101.0;
            port data : Common::DataPort;
        }
        part def Controller_0201 :> Common::Component {
            attribute :>> mass = 1.50 [kg];
            attribute :>> cost = 201.0;
            port supply : Common::PowerPort;
            part sensors : Sensor_0201[2];
            action smooth : Common::Process;
            action forward : Common::Process;
            succession first smooth then forward;
            exhibit state lifecycle : Common::Lifecycle;
        }
        requirement controllerMass_0201 : Common::MassLimit {
            subject component : Controller_0201;
            attribute :>> limit = 2.0 [kg];
        }
    }

    package Subsystem_0202 {
        part def Sensor_0202 :> Common::Component {
            attribute :>> mass = 0.22 [kg];
            attribute :>> cost = 32.0;
            attribute range : Real = 102.0;
            port data : Common::DataPort;
        }
        part def Controller_0202 :> Common::Component {
            attribute :>> mass = 1.60 [kg];
            attribute :>> cost = 202.0;
            port supply : Common::PowerPort;
            part sensors : Sensor_0202[2];
            action smooth : Common::Process;
            action forward : Common::Process;
            succession first smooth then forward;
            exhibit state lifecycle : Common::Lifecycle;
        }
        requirement controllerMass_0202 : Common::MassLimit {
            subject component : Controller_0202;
            attribute :>> limit = 2.0 [kg];
        }
    }

    package Subsystem_0203 {
        part def Sensor_0203 :> Common::Component {
            attribute :>> mass = 0.23 [kg];
            attribute :>> cost = 33.0;
            attribute range : Real = 103.0;
            port data : Common::DataPort;
        }
        part def Controller_0203 :> Common::Component {
            attribute :>> mass = 1.00 [kg];
            attribute :>> cost = 203.0;
            port supply : Common::PowerPort;
            part sensors : Sensor_0203[2];
            action smooth : Common::Process;
            action forward : Common::Process;
            succession first smooth then forward;
            exhibit state lifecycle : Common::Lifecycle;
        }
        requirement controllerMass_0203 : Common::MassLimit {
            subject component : Controller_0203;
            attribute :>> limit = 2.0 [kg];
        }
    }

    package Subsystem_0204 {
        part def Sensor_0204 :> Common::Component {
            attribute :>> mass = 0.24 [kg];
            attribute :>> cost = 34.0;
            attribute range : Real = 104.0;
            port data : Common::DataPort;
        }
        part def Controller_0204 :> Common::Component {
            attribute :>> mass = 1.10 [kg];
            attribute :>> cost = 204.0;
            port supply : Common::PowerPort;
            part sensors : Sensor_0204[2];
            action smooth : Common::Process;
            action forward : Common::Process;
            succession first smooth then forward;
            exhibit state lifecycle : Common::Lifecycle;
        }
        requirement controllerMass_0204 : Common::MassLimit {
            subject component : Controller_0204;
            attribute :>> limit = 2.0 [kg];
        }
    }

    package Subsystem_0205 {
        part def Sensor_0205 :> Common::Component {
            attribute :>> mass = 0.20 [kg];
            attribute :>> cost = 35.0;
            attribute range : Real = 105.0;
            port data : Common::DataPort;
        }
        part def Controller_0205 :> Common::Component {
            attribute :>> mass = 1.20 [kg];
            attribute :>> cost = 205.0;
            port supply : Common::PowerPort;
            part sensors : Sensor_0205[2];
            action smooth : Common::Process;
            action forward : Common::Process;
            succession first smooth then forward;
            exhibit state lifecycle : Common::Lifecycle;
        }
        requirement controllerMass_0205 : Common::MassLimit {
            subject component : Controller_0205;
            attribute :>> limit = 2.0 [kg];
        }
    }

    package Subsystem_0206 {
        part def Sensor_0206 :> Common::Component {
            attribute :>> mass = 0.21 [kg];
            attribute :>> cost = 36.0;
            attribute range : Real = 106.0;
            port data : Common::DataPort;
        }
        part def Controller_0206 :> Common::Component {
            attribute :>> mass = 1.30 [kg];
            attribute :>> cost = 206.0;
            port supply : Common::PowerPort;
            part sensors : Sensor_0206[2];
            action smooth : Common::Process;
            action forward : Common::Process;
            succession first smooth then forward;
            exhibit state lifecycle : Common::Lifecycle;
        }
        requirement controllerMass_0206 : Common::MassLimit {
            subject component : Controller_0206;
            attribute :>> limit = 2.0 [kg];
        }
    }

    package Subsystem_0207 {
        part def Sensor_0207 :> Common::Component {
            attribute :>> mass = 0.22 [kg];
            attribute :>> cost = 37.0;
            attribute range : Real = 107.0;
            port data : Common::DataPort;
        }
        part def Controller_0207 :> Common::Component {
            attribute :>> mass = 1.40 [kg];
            attribute :>> cost = 207.0;
            port supply : Common::PowerPort;
            part sensors : Sensor_0207[2];
            action smooth : Common::Process;
            action forward : Common::Process;
            succession first smooth then forward;
            exhibit state lifecycle : Common::Lifecycle;
        }
        requirement controllerMass_0207 : Common::MassLimit {
            subject component : Controller_0207;
            attribute :>> limit = 2.0 [kg];
        }
    }

    package Subsystem_0208 {
        part def Sensor_0208 :> Common::Component {
            attribute :>> mass = 0.23 [kg];
            attribute :>> cost = 38.0;
            attribute range : Real = 108.0;
            port data : Common::DataPort;
        }
        part def Controller_0208 :> Common::Component {
            attribute :>> mass = 1.50 [kg];
            attribute :>> cost = 208.0;
            port supply : Common::PowerPort;
            part sensors : Sensor_0208[2];
            action smooth : Common::Process;
            action forward : Common::Process;
            succession first smooth then forward;
            exhibit state lifecycle : Common::Lifecycle;
        }
        requirement controllerMass_0208 : Common::MassLimit {
            subject component : Controller_0208;
            attribute :>> limit = 2.0 [kg];
        }
    }

    package Subsystem_0209 {
        part def Sensor_0209 :> Common::Component {
            attribute :>> mass = 0.24 [kg];
            attribute :>> cost = 39.0;
            attribute range : Real = 109.0;
            port data : Common::DataPort;
        }
        part def Controller_0209 :> Common::Component {
            attribute :>> mass = 1.60 [kg];
            attribute :>> cost = 209.0;
            port supply : Common::PowerPort;
            part sensors : Sensor_0209[2];
            action smooth : Common::Process;
            action forward : Common::Process;
            succession first smooth then forward;
            exhibit state lifecycle : Common::Lifecycle;
        }
        requirement controllerMass_0209 : Common::MassLimit {
            subject component : Controller_0209;
            attribute :>> limit = 2.0 [kg];
        }
    }

    package Subsystem_0210 {
        part def Sensor_0210 :> Common::Component {
            attribute :>> mass = 0.20 [kg];
            attribute :>> cost = 40.0;
            attribute range : Real = 110.0;
            port data : Common::DataPort;
        }
        part def Controller_0210 :> Common::Component {
            attribute :>> mass = 1.00 [kg];
            attribute :>> cost = 210.0;
            port supply : Common::PowerPort;
            part sensors : Sensor_0210[2];
            action smooth : Common::Process;
            action forward : Common::Process;
            succession first smooth then forward;
            exhibit state lifecycle : Common::Lifecycle;
        }
        requirement controllerMass_0210 : Common::MassLimit {
            subject component : Controller_0210;
            attribute :>> limit = 2.0 [kg];
        }
    }

    package Subsystem_0211 {
        part def Sensor_0211 :> Common::Component {
            attribute :>> mass = 0.21 [kg];
            attribute :>> cost = 41.0;
            attribute range : Real = 111.0;
            port data : Common::DataPort;
        }
        part def Controller_0211 :> Common::Component {
            attribute :>> mass = 1.10 [kg];
            attribute :>> cost = 211.0;
            port supply : Common::PowerPort;
            part sensors : Sensor_0211[2];
            action smooth : Common::Process;
            action forward : Common::Process;
            succession first smooth then forward;
            exhibit state lifecycle : Common::Lifecycle;
        }
        requirement controllerMass_0211 : Common::MassLimit {
            subject component : Controller_0211;
            attribute :>> limit = 2.0 [kg];
        }
    }

    package Subsystem_0212 {
        part def Sensor_0212 :> Common::Component {
            attribute :>> mass = 0.22 [kg];
            attribute :>> cost = 42.0;
            attribute range : Real = 112.0;
            port data : Common::DataPort;
        }
        part def Controller_0212 :> Common::Component {
            attribute :>> mass = 1.20 [kg];
            attribute :>> cost = 212.0;
            port supply : Common::PowerPort;
            part sensors : Sensor_0212[2];
            action smooth : Common::Process;
            action forward : Common::Process;
            succession first smooth then forward;
            exhibit state lifecycle : Common::Lifecycle;
        }
        requirement controllerMass_0212 : Common::MassLimit {
            subject component : Controller_0212;
            attribute :>> limit = 2.0 [kg];
        }
    }

    package Subsystem_0213 {
        part def Sensor_0213 :> Common::Component {
            attribute :>> mass = 0.23 [kg];
            attribute :>> cost = 43.0;
            attribute range : Real = 113.0;
            port data : Common::DataPort;
        }
        part def Controller_0213 :> Common::Component {
            attribute :>> mass = 1.30 [kg];
            attribute :>> cost = 213.0;
            port supply : Common::PowerPort;
            part sensors : Sensor_0213[2];
            action smooth : Common::Process;
            action forward : Common::Process;
            succession first smooth then forward;
            exhibit state lifecycle : Common::Lifecycle;
        }
        requirement controllerMass_0213 : Common::MassLimit {
            subject component : Controller_0213;
            attribute :>> limit = 2.0 [kg];
        }
    }

    package Subsystem_0214 {
        part def Sensor_0214 :> Common::Component {
            attribute :>> mass = 0.24 [kg];
            attribute :>> cost = 44.0;
            attribute range : Real = 114.0;
            port data : Common::DataPort;
        }
        part def Controller_0214 :> Common::Component {
            attribute :>> mass = 1.40 [kg];
            attribute :>> cost = 214.0;
            port supply : Common::PowerPort;
            part sensors : Sensor_0214[2];
            action smooth : Common::Process;
            action forward : Common::Process;
            succession first smooth then forward;
            exhibit state lifecycle : Common::Lifecycle;
        }
        requirement controllerMass_0214 : Common::MassLimit {
            subject component : Controller_0214;
            attribute :>> limit = 2.0 [kg];
        }
    }

    package Subsystem_0215 {
        part def Sensor_0215 :> Common::Component {
            attribute :>> mass = 0.20 [kg];
            attribute :>> cost = 45.0;
            attribute range : Real = 115.0;
            port data : Common::DataPort;
        }
        part def Controller_0215 :> Common::Component {
            attribute :>> mass = 1.50 [kg];
            attribute :>> cost = 215.0;
            port supply : Common::PowerPort;
            part sensors : Sensor_0215[2];
            action smooth : Common::Process;
            action forward : Common::Process;
            succession first smooth then forward;
            exhibit state lifecycle : Common::Lifecycle;
        }
        requirement controllerMass_0215 : Common::MassLimit {
            subject component : Controller_0215;
            attribute :>> limit = 2.0 [kg];
        }
    }

    package Subsystem_0216 {
        part def Sensor_0216 :> Common::Component {
            attribute :>> mass = 0.21 [kg];
            attribute :>> cost = 46.0;
            attribute range : Real = 116.0;
            port data : Common::DataPort;
        }
        part def Controller_0216 :> Common::Component {
            attribute :>> mass = 1.60 [kg];
            attribute :>> cost = 216.0;
            port supply : Common::PowerPort;
            part sensors : Sensor_0216[2];
            action smooth : Common::Process;
            action forward : Common::Process;
            succession first smooth then forward;
            exhibit state lifecycle : Common::Lifecycle;
        }
        requirement controllerMass_0216 : Common::MassLimit {
            subject component : Controller_0216;
            attribute :>> limit = 2.0 [kg];
        }
    }

    package Subsystem_0217 {
        part def Sensor_0217 :> Common::Component {
            attribute :>> mass = 0.22 [kg];
            attribute :>> cost = 47.0;
            attribute range : Real = 117.0;
            port data : Common::DataPort;
        }
        part def Controller_0217 :> Common::Component {
            attribute :>> mass = 1.00 [kg];
            attribute :>> cost = 217.0;
            port supply : Common::PowerPort;
            part sensors : Sensor_0217[2];
            action smooth : Common::Process;
            action forward : Common::Process;
            succession first smooth then forward;
            exhibit state lifecycle : Common::Lifecycle;
        }
        requirement controllerMass_0217 : Common::MassLimit {
            subject component : Controller_0217;
            attribute :>> limit = 2.0 [kg];
        }
    }

    package Subsystem_0218 {
        part def Sensor_0218 :> Common::Component {
            attribute :>> mass = 0.23 [kg];
            attribute :>> cost = 48.0;
            attribute range : Real = 118.0;
            port data : Common::DataPort;
        }
        part def Controller_0218 :> Common::Component {
            attribute :>> mass = 1.10 [kg];
            attribute :>> cost = 218.0;
            port supply : Common::PowerPort;
            part sensors : Sensor_0218[2];
            action smooth : Common::Process;
            action forward : Common::Process;
            succession first smooth then forward;
            exhibit state lifecycle : Common::Lifecycle;
        }
        requirement controllerMass_0218 : Common::MassLimit {
            subject component : Controller_0218;
            attribute :>> limit = 2.0 [kg];
        }
    }

    package Subsystem_0219 {
        part def Sensor_0219 :> Common::Component {
            attribute :>> mass = 0.24 [kg];
            attribute :>> cost = 49.0;
            attribute range : Real = 119.0;
            port data : Common::DataPort;
        }
        part def Controller_0219 :> Common::Component {
            attribute :>> mass = 1.20 [kg];
            attribute :>> cost = 219.0;
            port supply : Common::PowerPort;
            part sensors : Sensor_0219[2];
            action smooth : Common::Process;
            action forward : Common::Process;
            succession first smooth then forward;
            exhibit state lifecycle : Common::Lifecycle;
        }
        requirement controllerMass_0219 : Common::MassLimit {
            subject component : Controller_0219;
            attribute :>> limit = 2.0 [kg];
        }
    }

    package Subsystem_0220 {
        part def Sensor_0220 :> Common::Component {
            attribute :>> mass = 0.20 [kg];
            attribute :>> cost = 30.0;
            attribute range : Real = 120.0;
            port data : Common::DataPort;
        }
        part def Controller_0220 :> Common::Component {
            attribute :>> mass = 1.30 [kg];
            attribute :>> cost = 220.0;
            port supply : Common::PowerPort;
            part sensors : Sensor_0220[2];
            action smooth : Common::Process;
            action forward : Common::Process;
            succession first smooth then forward;
            exhibit state lifecycle : Common::Lifecycle;
        }
        requirement controllerMass_0220 : Common::MassLimit {
            subject component : Controller_0220;
            attribute :>> limit = 2.0 [kg];
        }
    }

    package Subsystem_0221 {
        part def Sensor_0221 :> Common::Component {
            attribute :>> mass = 0.21 [kg];
            attribute :>> cost = 31.0;
            attribute range : Real = 121.0;
            port data : Common::DataPort;
        }
        part def Controller_0221 :> Common::Component {
            attribute :>> mass = 1.40 [kg];
            attribute :>> cost = 221.0;
            port supply : Common::PowerPort;
            part sensors : Sensor_0221[2];
            action smooth : Common::Process;
            action forward : Common::Process;
            succession first smooth then forward;
            exhibit state lifecycle : Common::Lifecycle;
        }
        requirement controllerMass_0221 : Common::MassLimit {
            subject component : Controller_0221;
            attribute :>> limit = 2.0 [kg];
        }
    }

    package Subsystem_0222 {
        part def Sensor_0222 :> Common::Component {
            attribute :>> mass = 0.22 [kg];
            attribute :>> cost = 32.0;
            attribute range : Real = 122.0;
            port data : Common::DataPort;
        }
        part def Controller_0222 :> Common::Component {
            attribute :>> mass = 1.50 [kg];
            attribute :>> cost = 222.0;
            port supply : Common::PowerPort;
            part sensors : Sensor_0222[2];
            action smooth : Common::Process;
            action forward : Common::Process;
            succession first smooth then forward;
            exhibit state lifecycle : Common::Lifecycle;
        }
        requirement controllerMass_0222 : Common::MassLimit {
            subject component : Controller_0222;
            attribute :>> limit = 2.0 [kg];
        }
    }

    package Subsystem_0223 {
        part def Sensor_0223 :> Common::Component {
            attribute :>> mass = 0.23 [kg];
            attribute :>> cost = 33.0;
            attribute range : Real = 123.0;
            port data : Common::DataPort;
        }
        part def Controller_0223 :> Common::Component {
            attribute :>> mass = 1.60 [kg];
            attribute :>> cost = 223.0;
            port supply : Common::PowerPort;
            part sensors : Sensor_0223[2];
            action smooth : Common::Process;
            action forward : Common::Process;
            succession first smooth then forward;
            exhibit state lifecycle : Common::Lifecycle;
        }
        requirement controllerMass_0223 : Common::MassLimit {
            subject component : Controller_0223;
            attribute :>> limit = 2.0 [kg];
        }
    }

    package Subsystem_0224 {
        part def Sensor_0224 :> Common::Component {
            attribute :>> mass = 0.24 [kg];
            attribute :>> cost = 34.0;
            attribute range : Real = 124.0;
            port data : Common::DataPort;
        }
        part def Controller_0224 :> Common::Component {
            attribute :>> mass = 1.00 [kg];
            attribute :>> cost = 224.0;
            port supply : Common::PowerPort;
            part sensors : Sensor_0224[2];
            action smooth : Common::Process;
            action forward : Common::Process;
            succession first smooth then forward;
            exhibit state lifecycle : Common::Lifecycle;
        }
        requirement controllerMass_0224 : Common::MassLimit {
            subject component : Controller_0224;
            attribute :>> limit = 2.0 [kg];
        }
    }

    package Subsystem_0225 {
        part def Sensor_0225 :> Common::Component {
            attribute :>> mass = 0.20 [kg];
            attribute :>> cost = 35.0;
            attribute range : Real = 125.0;
            port data : Common::DataPort;
        }
        part def Controller_0225 :> Common::Component {
            attribute :>> mass = 1.10 [kg];
            attribute :>> cost = 225.0;
            port supply : Common::PowerPort;
            part sensors : Sensor_0225[2];
            action smooth : Common::Process;
            action forward : Common::Process;
            succession first smooth then forward;
            exhibit state lifecycle : Common::Lifecycle;
        }
        requirement controllerMass_0225 : Common::MassLimit {
            subject component : Controller_0225;
            attribute :>> limit = 2.0 [kg];
        }
    }

    package Subsystem_0226 {
        part def Sensor_0226 :> Common::Component {
            attribute :>> mass = 0.21 [kg];
            attribute :>> cost = 36.0;
            attribute range : Real = 126.0;
            port data : Common::DataPort;
        }
        part def Controller_0226 :> Common::Component {
            attribute :>> mass = 1.20 [kg];
            attribute :>> cost = 226.0;
            port supply : Common::PowerPort;
            part sensors : Sensor_0226[2];
            action smooth : Common::Process;
            action forward : Common::Process;
            succession first smooth then forward;
            exhibit state lifecycle : Common::Lifecycle;
        }
        requirement controllerMass_0226 : Common::MassLimit {
            subject component : Controller_0226;
            attribute :>> limit = 2.0 [kg];
        }
    }

    package Subsystem_0227 {
        part def Sensor_0227 :> Common::Component {
            attribute :>> mass = 0.22 [kg];
            attribute :>> cost = 37.0;
            attribute range : Real = 127.0;
            port data : Common::DataPort;
        }
        part def Controller_0227 :> Common::Component {
            attribute :>> mass = 1.30 [kg];
            attribute :>> cost = 227.0;
            port supply : Common::PowerPort;
            part sensors : Sensor_0227[2];
            action smooth : Common::Process;
            action forward : Common::Process;
            succession first smooth then forward;
            exhibit state lifecycle : Common::Lifecycle;
        }
        requirement controllerMass_0227 : Common::MassLimit {
            subject component : Controller_0227;
            attribute :>> limit = 2.0 [kg];
        }
    }

    package Subsystem_0228 {
        part def Sensor_0228 :> Common::Component {
            attribute :>> mass = 0.23 [kg];
            attribute :>> cost = 38.0;
            attribute range : Real = 128.0;
            port data : Common::DataPort;
        }
        part def Controller_0228 :> Common::Component {
            attribute :>> mass = 1.40 [kg];
            attribute :>> cost = 228.0;
            port supply : Common::PowerPort;
            part sensors : Sensor_0228[2];
            action smooth : Common::Process;
            action forward : Common::Process;
            succession first smooth then forward;
            exhibit state lifecycle : Common::Lifecycle;
        }
        requirement controllerMass_0228 : Common::MassLimit {
            subject component : Controller_0228;
            attribute :>> limit = 2.0 [kg];
        }
    }

    package Subsystem_0229 {
        part def Sensor_0229 :> Common::Component {
            attribute :>> mass = 0.24 [kg];
            attribute :>> cost = 39.0;
            attribute range : Real = 129.0;
            port data : Common::DataPort;
        }
        part def Controller_0229 :> Common::Component {
            attribute :>> mass = 1.50 [kg];
            attribute :>> cost = 229.0;
            port supply : Common::PowerPort;
            part sensors : Sensor_0229[2];
            action smooth : Common::Process;
            action forward : Common::Process;
            succession first smooth then forward;
            exhibit state lifecycle : Common::Lifecycle;
        }
        requirement controllerMass_0229 : Common::MassLimit {
            subject component : Controller_0229;
            attribute :>> limit = 2.0 [kg];
        }
    }

    package Subsystem_0230 {
        part def Sensor_0230 :> Common::Component {
            attribute :>> mass = 0.20 [kg];
            attribute :>> cost = 40.0;
            attribute range : Real = 130.0;
            port data : Common::DataPort;
        }
        part def Controller_0230 :> Common::Component {
            attribute :>> mass = 1.60 [kg];
            attribute :>> cost = 230.0;
            port supply : Common::PowerPort;
            part sensors : Sensor_0230[2];
            action smooth : Common::Process;
            action forward : Common::Process;
            succession first smooth then forward;
            exhibit state lifecycle : Common::Lifecycle;
        }
        requirement controllerMass_0230 : Common::MassLimit {
            subject component : Controller_0230;
            attribute :>> limit = 2.0 [kg];
        }
    }

    package Subsystem_0231 {
        part def Sensor_0231 :> Common::Component {
            attribute :>> mass = 0.21 [kg];
            attribute :>> cost = 41.0;
            attribute range : Real = 131.0;
            port data : Common::DataPort;
        }
        part def Controller_0231 :> Common::Component {
            attribute :>> mass = 1.00 [kg];
            attribute :>> cost = 231.0;
            port supply : Common::PowerPort;
            part sensors : Sensor_0231[2];
            action smooth : Common::Process;
            action forward : Common::Process;
            succession first smooth then forward;
            exhibit state lifecycle : Common::Lifecycle;
        }
        requirement controllerMass_0231 : Common::MassLimit {
            subject component : Controller_0231;
            attribute :>> limit = 2.0 [kg];
        }
    }

    package Subsystem_0232 {
        part def Sensor_0232 :> Common::Component {
            attribute :>> mass = 0.22 [kg];
            attribute :>> cost = 42.0;
            attribute range : Real = 132.0;
            port data : Common::DataPort;
        }
        part def Controller_0232 :> Common::Component {
            attribute :>> mass = 1.10 [kg];
            attribute :>> cost = 232.0;
            port supply : Common::PowerPort;
            part sensors : Sensor_0232[2];
            action smooth : Common::Process;
            action forward : Common::Process;
            succession first smooth then forward;
            exhibit state lifecycle : Common::Lifecycle;
        }
        requirement controllerMass_0232 : Common::MassLimit {
            subject component : Controller_0232;
            attribute :>> limit = 2.0 [kg];
        }
    }

    package Subsystem_0233 {
        part def Sensor_0233 :> Common::Component {
            attribute :>> mass = 0.23 [kg];
            attribute :>> cost = 43.0;
            attribute range : Real = 133.0;
            port data : Common::DataPort;
        }
        part def Controller_0233 :> Common::Component {
            attribute :>> mass = 1.20 [kg];
            attribute :>> cost = 233.0;
            port supply : Common::PowerPort;
            part sensors : Sensor_0233[2];
            action smooth : Common::Process;
            action forward : Common::Process;
            succession first smooth then forward;
            exhibit state lifecycle : Common::Lifecycle;
        }
        requirement controllerMass_0233 : Common::MassLimit {
            subject component : Controller_0233;
            attribute :>> limit = 2.0 [kg];
        }
    }

    package Subsystem_0234 {
        part def Sensor_0234 :> Common::Component {
            attribute :>> mass = 0.24 [kg];
            attribute :>> cost = 44.0;
            attribute range : Real = 134.0;
            port data : Common::DataPort;
        }
        part def Controller_0234 :> Common::Component {
            attribute :>> mass = 1.30 [kg];
            attribute :>> cost = 234.0;
            port supply : Common::PowerPort;
            part sensors : Sensor_0234[2];
            action smooth : Common::Process;
            action forward : Common::Process;
            succession first smooth then forward;
            exhibit state lifecycle : Common::Lifecycle;
        }
        requirement controllerMass_0234 : Common::MassLimit {
            subject component : Controller_0234;
            attribute :>> limit = 2.0 [kg];
        }
    }

    package Subsystem_0235 {
        part def Sensor_0235 :> Common::Component {
            attribute :>> mass = 0.20 [kg];
            attribute :>> cost = 45.0;
            attribute range : Real = 135.0;
            port data : Common::DataPort;
        }
        part def Controller_0235 :> Common::Component {
            attribute :>> mass = 1.40 [kg];
            attribute :>> cost = 235.0;
            port supply : Common::PowerPort;
            part sensors : Sensor_0235[2];
            action smooth : Common::Process;
            action forward : Common::Process;
            succession first smooth then forward;
            exhibit state lifecycle : Common::Lifecycle;
        }
        requirement controllerMass_0235 : Common::MassLimit {
            subject component : Controller_0235;
            attribute :>> limit = 2.0 [kg];
        }
    }

    package Subsystem_0236 {
        part def Sensor_0236 :> Common::Component {
            attribute :>> mass = 0.21 [kg];
            attribute :>> cost = 46.0;
            attribute range : Real = 136.0;
            port data : Common::DataPort;
        }
        part def Controller_0236 :> Common::Component {
            attribute :>> mass = 1.50 [kg];
            attribute :>> cost = 236.0;
            port supply : Common::PowerPort;
            part sensors : Sensor_0236[2];
            action smooth : Common::Process;
            action forward : Common::Process;
            succession first smooth then forward;
            exhibit state lifecycle : Common::Lifecycle;
        }
        requirement controllerMass_0236 : Common::MassLimit {
            subject component : Controller_0236;
            attribute :>> limit = 2.0 [kg];
        }
    }

    package Subsystem_0237 {
        part def Sensor_0237 :> Common::Component {
            attribute :>> mass = 0.22 [kg];
            attribute :>> cost = 47.0;
            attribute range : Real = 137.0;
            port data : Common::DataPort;
        }
        part def Controller_0237 :> Common::Component {
            attribute :>> mass = 1.60 [kg];
            attribute :>> cost = 237.0;
            port supply : Common::PowerPort;
            part sensors : Sensor_0237[2];
            action smooth : Common::Process;
            action forward : Common::Process;
            succession first smooth then forward;
            exhibit state lifecycle : Common::Lifecycle;
        }
        requirement controllerMass_0237 : Common::MassLimit {
            subject component : Controller_0237;
            attribute :>> limit = 2.0 [kg];
        }
    }

    package Subsystem_0238 {
        part def Sensor_0238 :> Common::Component {
            attribute :>> mass = 0.23 [kg];
            attribute :>> cost = 48.0;
            attribute range : Real = 138.0;
            port data : Common::DataPort;
        }
        part def Controller_0238 :> Common::Component {
            attribute :>> mass = 1.00 [kg];
            attribute :>> cost = 238.0;
            port supply : Common::PowerPort;
            part sensors : Sensor_0238[2];
            action smooth : Common::Process;
            action forward : Common::Process;
            succession first smooth then forward;
            exhibit state lifecycle : Common::Lifecycle;
        }
        requirement controllerMass_0238 : Common::MassLimit {
            subject component : Controller_0238;
            attribute :>> limit = 2.0 [kg];
        }
    }

    package Subsystem_0239 {
        part def Sensor_0239 :> Common::Component {
            attribute :>> mass = 0.24 [kg];
            attribute :>> cost = 49.0;
            attribute range : Real = 139.0;
            port data : Common::DataPort;
        }
        part def Controller_0239 :> Common::Component {
            attribute :>> mass = 1.10 [kg];
            attribute :>> cost = 239.0;
            port supply : Common::PowerPort;
            part sensors : Sensor_0239[2];
            action smooth : Common::Process;
            action forward : Common::Process;
            succession first smooth then forward;
            exhibit state lifecycle : Common::Lifecycle;
        }
        requirement controllerMass_0239 : Common::MassLimit {
            subject component : Controller_0239;
            attribute :>> limit = 2.0 [kg];
        }
    }

    package Subsystem_0240 {
        part def Sensor_0240 :> Common::Component {
            attribute :>> mass = 0.20 [kg];
            attribute :>> cost = 30.0;
            attribute range : Real = 140.0;
            port data : Common::DataPort;
        }
        part def Controller_0240 :> Common::Component {
            attribute :>> mass = 1.20 [kg];
            attribute :>> cost = 240.0;
            port supply : Common::PowerPort;
            part sensors : Sensor_0240[2];
            action smooth : Common::Process;
            action forward : Common::Process;
            succession first smooth then forward;
            exhibit state lifecycle : Common::Lifecycle;
        }
        requirement controllerMass_0240 : Common::MassLimit {
            subject component : Controller_0240;
            attribute :>> limit = 2.0 [kg];
        }
    }

    package Subsystem_0241 {
        part def Sensor_0241 :> Common::Component {
            attribute :>> mass = 0.21 [kg];
            attribute :>> cost = 31.0;
            attribute range : Real = 141.0;
            port data : Common::DataPort;
        }
        part def Controller_0241 :> Common::Component {
            attribute :>> mass = 1.30 [kg];
            attribute :>> cost = 241.0;
            port supply : Common::PowerPort;
            part sensors : Sensor_0241[2];
            action smooth : Common::Process;
            action forward : Common::Process;
            succession first smooth then forward;
            exhibit state lifecycle : Common::Lifecycle;
        }
        requirement controllerMass_0241 : Common::MassLimit {
            subject component : Controller_0241;
            attribute :>> limit = 2.0 [kg];
        }
    }

    package Subsystem_0242 {
        part def Sensor_0242 :> Common::Component {
            attribute :>> mass = 0.22 [kg];
            attribute :>> cost = 32.0;
            attribute range : Real = 142.0;
            port data : Common::DataPort;
        }
        part def Controller_0242 :> Common::Component {
            attribute :>> mass = 1.40 [kg];
            attribute :>> cost = 242.0;
            port supply : Common::PowerPort;
            part sensors : Sensor_0242[2];
            action smooth : Common::Process;
            action forward : Common::Process;
            succession first smooth then forward;
            exhibit state lifecycle : Common::Lifecycle;
        }
        requirement controllerMass_0242 : Common::MassLimit {
            subject component : Controller_0242;
            attribute :>> limit = 2.0 [kg];
        }
    }

    package Subsystem_0243 {
        part def Sensor_0243 :> Common::Component {
            attribute :>> mass = 0.23 [kg];
            attribute :>> cost = 33.0;
            attribute range : Real = 143.0;
            port data : Common::DataPort;
        }
        part def Controller_0243 :> Common::Component {
            attribute :>> mass = 1.50 [kg];
            attribute :>> cost = 243.0;
            port supply : Common::PowerPort;
            part sensors : Sensor_0243[2];
            action smooth : Common::Process;
            action forward : Common::Process;
            succession first smooth then forward;
            exhibit state lifecycle : Common::Lifecycle;
        }
        requirement controllerMass_0243 : Common::MassLimit {
            subject component : Controller_0243;
            attribute :>> limit = 2.0 [kg];
        }
    }

    package Subsystem_0244 {
        part def Sensor_0244 :> Common::Component {
            attribute :>> mass = 0.24 [kg];
            attribute :>> cost = 34.0;
            attribute range : Real = 144.0;
            port data : Common::DataPort;
        }
        part def Controller_0244 :> Common::Component {
            attribute :>> mass = 1.60 [kg];
            attribute :>> cost = 244.0;
            port supply : Common::PowerPort;
            part sensors : Sensor_0244[2];
            action smooth : Common::Process;
            action forward : Common::Process;
            succession first smooth then forward;
            exhibit state lifecycle : Common::Lifecycle;
        }
        requirement controllerMass_0244 : Common::MassLimit {
            subject component : Controller_0244;
            attribute :>> limit = 2.0 [kg];
        }
    }

    package Subsystem_0245 {
        part def Sensor_0245 :> Common::Component {
            attribute :>> mass = 0.20 [kg];
            attribute :>> cost = 35.0;
            attribute range : Real = 145.0;
            port data : Common::DataPort;
        }
        part def Controller_0245 :> Common::Component {
            attribute :>> mass = 1.00 [kg];
            attribute :>> cost = 245.0;
            port supply : Common::PowerPort;
            part sensors : Sensor_0245[2];
            action smooth : Common::Process;
            action forward : Common::Process;
            succession first smooth then forward;
            exhibit state lifecycle : Common::Lifecycle;
        }
        requirement controllerMass_0245 : Common::MassLimit {
            subject component : Controller_0245;
            attribute :>> limit = 2.0 [kg];
        }
    }

    package Subsystem_0246 {
        part def Sensor_0246 :> Common::Component {
            attribute :>> mass = 0.21 [kg];
            attribute :>> cost = 36.0;
            attribute range : Real = 146.0;
            port data : Common::DataPort;
        }
        part def Controller_0246 :> Common::Component {
            attribute :>> mass = 1.10 [kg];
            attribute :>> cost = 246.0;
            port supply : Common::PowerPort;
            part sensors : Sensor_0246[2];
            action smooth : Common::Process;
            action forward : Common::Process;
            succession first smooth then forward;
            exhibit state lifecycle : Common::Lifecycle;
        }
        requirement controllerMass_0246 : Common::MassLimit {
            subject component : Controller_0246;
            attribute :>> limit = 2.0 [kg];
        }
    }

    package Subsystem_0247 {
        part def Sensor_0247 :> Common::Component {
            attribute :>> mass = 0.22 [kg];
            attribute :>> cost = 37.0;
            attribute range : Real = 147.0;
            port data : Common::DataPort;
        }
        part def Controller_0247 :> Common::Component {
            attribute :>> mass = 1.20 [kg];
            attribute :>> cost = 247.0;
            port supply : Common::PowerPort;
            part sensors : Sensor_0247[2];
            action smooth : Common::Process;
            action forward : Common::Process;
            succession first smooth then forward;
            exhibit state lifecycle : Common::Lifecycle;
        }
        requirement controllerMass_0247 : Common::MassLimit {
            subject component : Controller_0247;
            attribute :>> limit = 2.0 [kg];
        }
    }

    package Subsystem_0248 {
        part def Sensor_0248 :> Common::Component {
            attribute :>> mass = 0.23 [kg];
            attribute :>> cost = 38.0;
            attribute range : Real = 148.0;
            port data : Common::DataPort;
        }
        part def Controller_0248 :> Common::Component {
            attribute :>> mass = 1.30 [kg];
            attribute :>> cost = 248.0;
            port supply : Common::PowerPort;
            part sensors : Sensor_0248[2];
            action smooth : Common::Process;
            action forward : Common::Process;
            succession first smooth then forward;
            exhibit state lifecycle : Common::Lifecycle;
        }
        requirement controllerMass_0248 : Common::MassLimit {
            subject component : Controller_0248;
            attribute :>> limit = 2.0 [kg];
        }
    }

    package Subsystem_0249 {
        part def Sensor_0249 :> Common::Component {
            attribute :>> mass = 0.24 [kg];
            attribute :>> cost = 39.0;
            attribute range : Real = 149.0;
            port data : Common::DataPort;
        }
        part def Controller_0249 :> Common::Component {
            attribute :>> mass = 1.40 [kg];
            attribute :>> cost = 249.0;
            port supply : Common::PowerPort;
            part sensors : Sensor_0249[2];
            action smooth : Common::Process;
            action forward : Common::Process;
            succession first smooth then forward;
            exhibit state lifecycle : Common::Lifecycle;
        }
        requirement controllerMass_0249 : Common::MassLimit {
            subject component : Controller_0249;
            attribute :>> limit = 2.0 [kg];
        }
    }

    package Subsystem_0250 {
        part def Sensor_0250 :> Common::Component {
            attribute :>> mass = 0.20 [kg];
            attribute :>> cost = 40.0;
            attribute range : Real = 100.0;
            port data : Common::DataPort;
        }
        part def Controller_0250 :> Common::Component {
            attribute :>> mass = 1.50 [kg];
            attribute :>> cost = 250.0;
            port supply : Common::PowerPort;
            part sensors : Sensor_0250[2];
            action smooth : Common::Process;
            action forward : Common::Process;
            succession first smooth then forward;
            exhibit state lifecycle : Common::Lifecycle;
        }
        requirement controllerMass_0250 : Common::MassLimit {
            subject component : Controller_0250;
            attribute :>> limit = 2.0 [kg];
        }
    }

    package Subsystem_0251 {
        part def Sensor_0251 :> Common::Component {
            attribute :>> mass = 0.21 [kg];
            attribute :>> cost = 41.0;
            attribute range : Real = 101.0;
            port data : Common::DataPort;
        }
        part def Controller_0251 :> Common::Component {
            attribute :>> mass = 1.60 [kg];
            attribute :>> cost = 251.0;
            port supply : Common::PowerPort;
            part sensors : Sensor_0251[2];
            action smooth : Common::Process;
            action forward : Common::Process;
            succession first smooth then forward;
            exhibit state lifecycle : Common::Lifecycle;
        }
        requirement controllerMass_0251 : Common::MassLimit {
            subject component : Controller_0251;
            attribute :>> limit = 2.0 [kg];
        }
    }

    package Subsystem_0252 {
        part def Sensor_0252 :> Common::Component {
            attribute :>> mass = 0.22 [kg];
            attribute :>> cost = 42.0;
            attribute range : Real = 102.0;
            port data : Common::DataPort;
        }
        part def Controller_0252 :> Common::Component {
            attribute :>> mass = 1.00 [kg];
            attribute :>> cost = 252.0;
            port supply : Common::PowerPort;
            part sensors : Sensor_0252[2];
            action smooth : Common::Process;
            action forward : Common::Process;
            succession first smooth then forward;
            exhibit state lifecycle : Common::Lifecycle;
        }
        requirement controllerMass_0252 : Common::MassLimit {
            subject component : Controller_0252;
            attribute :>> limit = 2.0 [kg];
        }
    }

    package Subsystem_0253 {
        part def Sensor_0253 :> Common::Component {
            attribute :>> mass = 0.23 [kg];
            attribute :>> cost = 43.0;
            attribute range : Real = 103.0;
            port data : Common::DataPort;
        }
        part def Controller_0253 :> Common::Component {
            attribute :>> mass = 1.10 [kg];
            attribute :>> cost = 253.0;
            port supply : Common::PowerPort;
            part sensors : Sensor_0253[2];
            action smooth : Common::Process;
            action forward : Common::Process;
            succession first smooth then forward;
            exhibit state lifecycle : Common::Lifecycle;
        }
        requirement controllerMass_0253 : Common::MassLimit {
            subject component : Controller_0253;
            attribute :>> limit = 2.0 [kg];
        }
    }

    package Subsystem_0254 {
        part def Sensor_0254 :> Common::Component {
            attribute :>> mass = 0.24 [kg];
            attribute :>> cost = 44.0;
            attribute range : Real = 104.0;
            port data : Common::DataPort;
        }
        part def Controller_0254 :> Common::Component {
            attribute :>> mass = 1.20 [kg];
            attribute :>> cost = 254.0;
            port supply : Common::PowerPort;
            part sensors : Sensor_0254[2];
            action smooth : Common::Process;
            action forward : Common::Process;
            succession first smooth then forward;
            exhibit state lifecycle : Common::Lifecycle;
        }
        requirement controllerMass_0254 : Common::MassLimit {
            subject component : Controller_0254;
            attribute :>> limit = 2.0 [kg];
        }
    }

    package Subsystem_0255 {
        part def Sensor_0255 :> Common::Component {
            attribute :>> mass = 0.20 [kg];
            attribute :>> cost = 45.0;
            attribute range : Real = 105.0;
            port data : Common::DataPort;
        }
        part def Controller_0255 :> Common::Component {
            attribute :>> mass = 1.30 [kg];
            attribute :>> cost = 255.0;
            port supply : Common::PowerPort;
            part sensors : Sensor_0255[2];
            action smooth : Common::Process;
            action forward : Common::Process;
            succession first smooth then forward;
            exhibit state lifecycle : Common::Lifecycle;
        }
        requirement controllerMass_0255 : Common::MassLimit {
            subject component : Controller_0255;
            attribute :>> limit = 2.0 [kg];
        }
    }

    package Subsystem_0256 {
        part def Sensor_0256 :> Common::Component {
            attribute :>> mass = 0.21 [kg];
            attribute :>> cost = 46.0;
            attribute range : Real = 106.0;
            port data : Common::DataPort;
        }
        part def Controller_0256 :> Common::Component {
            attribute :>> mass = 1.40 [kg];
            attribute :>> cost = 256.0;
            port supply : Common::PowerPort;
            part sensors : Sensor_0256[2];
            action smooth : Common::Process;
            action forward : Common::Process;
            succession first smooth then forward;
            exhibit state lifecycle : Common::Lifecycle;
        }
        requirement controllerMass_0256 : Common::MassLimit {
            subject component : Controller_0256;
            attribute :>> limit = 2.0 [kg];
        }
    }

    package Subsystem_0257 {
        part def Sensor_0257 :> Common::Component {
            attribute :>> mass = 0.22 [kg];
            attribute :>> cost = 47.0;
            attribute range : Real = 107.0;
            port data : Common::DataPort;
        }
        part def Controller_0257 :> Common::Component {
            attribute :>> mass = 1.50 [kg];
            attribute :>> cost = 257.0;
            port supply : Common::PowerPort;
            part sensors : Sensor_0257[2];
            action smooth : Common::Process;
            action forward : Common::Process;
            succession first smooth then forward;
            exhibit state lifecycle : Common::Lifecycle;
        }
        requirement controllerMass_0257 : Common::MassLimit {
            subject component : Controller_0257;
            attribute :>> limit = 2.0 [kg];
        }
    }

    package Subsystem_0258 {
        part def Sensor_0258 :> Common::Component {
            attribute :>> mass = 0.23 [kg];
            attribute :>> cost = 48.0;
            attribute range : Real = 108.0;
            port data : Common::DataPort;
        }
        part def Controller_0258 :> Common::Component {
            attribute :>> mass = 1.60 [kg];
            attribute :>> cost = 258.0;
            port supply : Common::PowerPort;
            part sensors : Sensor_0258[2];
            action smooth : Common::Process;
            action forward : Common::Process;
            succession first smooth then forward;
            exhibit state lifecycle : Common::Lifecycle;
        }
        requirement controllerMass_0258 : Common::MassLimit {
            subject component : Controller_0258;
            attribute :>> limit = 2.0 [kg];
        }
    }

    package Subsystem_0259 {
        part def Sensor_0259 :> Common::Component {
            attribute :>> mass = 0.24 [kg];
            attribute :>> cost = 49.0;
            attribute range : Real = 109.0;
            port data : Common::DataPort;
        }
        part def Controller_0259 :> Common::Component {
            attribute :>> mass = 1.00 [kg];
            attribute :>> cost = 259.0;
            port supply : Common::PowerPort;
            part sensors : Sensor_0259[2];
            action smooth : Common::Process;
            action forward : Common::Process;
            succession first smooth then forward;
            exhibit state lifecycle : Common::Lifecycle;
        }
        requirement controllerMass_0259 : Common::MassLimit {
            subject component : Controller_0259;
            attribute :>> limit = 2.0 [kg];
        }
    }

    package Subsystem_0260 {
        part def Sensor_0260 :> Common::Component {
            attribute :>> mass = 0.20 [kg];
            attribute :>> cost = 30.0;
            attribute range : Real = 110.0;
            port data : Common::DataPort;
        }
        part def Controller_0260 :> Common::Component {
            attribute :>> mass = 1.10 [kg];
            attribute :>> cost = 260.0;
            port supply : Common::PowerPort;
            part sensors : Sensor_0260[2];
            action smooth : Common::Process;
            action forward : Common::Process;
            succession first smooth then forward;
            exhibit state lifecycle : Common::Lifecycle;
        }
        requirement controllerMass_0260 : Common::MassLimit {
            subject component : Controller_0260;
            attribute :>> limit = 2.0 [kg];
        }
    }

    package Subsystem_0261 {
        part def Sensor_0261 :> Common::Component {
            attribute :>> mass = 0.21 [kg];
            attribute :>> cost = 31.0;
            attribute range : Real = 111.0;
            port data : Common::DataPort;
        }
        part def Controller_0261 :> Common::Component {
            attribute :>> mass = 1.20 [kg];
            attribute :>> cost = 261.0;
            port supply : Common::PowerPort;
            part sensors : Sensor_0261[2];
            action smooth : Common::Process;
            action forward : Common::Process;
            succession first smooth then forward;
            exhibit state lifecycle : Common::Lifecycle;
        }
        requirement controllerMass_0261 : Common::MassLimit {
            subject component : Controller_0261;
            attribute :>> limit = 2.0 [kg];
        }
    }

    package Subsystem_0262 {
        part def Sensor_0262 :> Common::Component {
            attribute :>> mass = 0.22 [kg];
            attribute :>> cost = 32.0;
            attribute range : Real = 112.0;
            port data : Common::DataPort;
        }
        part def Controller_0262 :> Common::Component {
            attribute :>> mass = 1.30 [kg];
            attribute :>> cost = 262.0;
            port supply : Common::PowerPort;
            part sensors : Sensor_0262[2];
            action smooth : Common::Process;
            action forward : Common::Process;
            succession first smooth then forward;
            exhibit state lifecycle : Common::Lifecycle;
        }
        requirement controllerMass_0262 : Common::MassLimit {
            subject component : Controller_0262;
            attribute :>> limit = 2.0 [kg];
        }
    }

    package Subsystem_0263 {
        part def Sensor_0263 :> Common::Component {
            attribute :>> mass = 0.23 [kg];
            attribute :>> cost = 33.0;
            attribute range : Real = 113.0;
            port data : Common::DataPort;
        }
        part def Controller_0263 :> Common::Component {
            attribute :>> mass = 1.40 [kg];
            attribute :>> cost = 263.0;
            port supply : Common::PowerPort;
            part sensors : Sensor_0263[2];
            action smooth : Common::Process;
            action forward : Common::Process;
            succession first smooth then forward;
            exhibit state lifecycle : Common::Lifecycle;
        }
        requirement controllerMass_0263 : Common::MassLimit {
            subject component : Controller_0263;
            attribute :>> limit = 2.0 [kg];
        }
    }

    package Subsystem_0264 {
        part def Sensor_0264 :> Common::Component {
            attribute :>> mass = 0.24 [kg];
            attribute :>> cost = 34.0;
            attribute range : Real = 114.0;
            port data : Common::DataPort;
        }
        part def Controller_0264 :> Common::Component {
            attribute :>> mass = 1.50 [kg];
            attribute :>> cost = 264.0;
            port supply : Common::PowerPort;
            part sensors : Sensor_0264[2];
            action smooth : Common::Process;
            action forward : Common::Process;
            succession first smooth then forward;
            exhibit state lifecycle : Common::Lifecycle;
        }
        requirement controllerMass_0264 : Common::MassLimit {
            subject component : Controller_0264;
            attribute :>> limit = 2.0 [kg];
        }
    }

    package Subsystem_0265 {
        part def Sensor_0265 :> Common::Component {
            attribute :>> mass = 0.20 [kg];
            attribute :>> cost = 35.0;
            attribute range : Real = 115.0;
            port data : Common::DataPort;
        }
        part def Controller_0265 :> Common::Component {
            attribute :>> mass = 1.60 [kg];
            attribute :>> cost = 265.0;
            port supply : Common::PowerPort;
            part sensors : Sensor_0265[2];
            action smooth : Common::Process;
            action forward : Common::Process;
            succession first smooth then forward;
            exhibit state lifecycle : Common::Lifecycle;
        }
        requirement controllerMass_0265 : Common::MassLimit {
            subject component : Controller_0265;
            attribute :>> limit = 2.0 [kg];
        }
    }

    package Subsystem_0266 {
        part def Sensor_0266 :> Common::Component {
            attribute :>> mass = 0.21 [kg];
            attribute :>> cost = 36.0;
            attribute range : Real = 116.0;
            port data : Common::DataPort;
        }
        part def Controller_0266 :> Common::Component {
            attribute :>> mass = 1.00 [kg];
            attribute :>> cost = 266.0;
            port supply : Common::PowerPort;
            part sensors : Sensor_0266[2];
            action smooth : Common::Process;
            action forward : Common::Process;
            succession first smooth then forward;
            exhibit state lifecycle : Common::Lifecycle;
        }
        requirement controllerMass_0266 : Common::MassLimit {
            subject component : Controller_0266;
            attribute :>> limit = 2.0 [kg];
        }
    }

    package Subsystem_0267 {
        part def Sensor_0267 :> Common::Component {
            attribute :>> mass = 0.22 [kg];
            attribute :>> cost = 37.0;
            attribute range : Real = 117.0;
            port data : Common::DataPort;
        }
        part def Controller_0267 :> Common::Component {
            attribute :>> mass = 1.10 [kg];
            attribute :>> cost = 267.0;
            port supply : Common::PowerPort;
            part sensors : Sensor_0267[2];
            action smooth : Common::Process;
            action forward : Common::Process;
            succession first smooth then forward;
            exhibit state lifecycle : Common::Lifecycle;
        }
        requirement controllerMass_0267 : Common::MassLimit {
            subject component : Controller_0267;
            attribute :>> limit = 2.0 [kg];
        }
    }

    package Subsystem_0268 {
        part def Sensor_0268 :> Common::Component {
            attribute :>> mass = 0.23 [kg];
            attribute :>> cost = 38.0;
            attribute range : Real = 118.0;
            port data : Common::DataPort;
        }
        part def Controller_0268 :> Common::Component {
            attribute :>> mass = 1.20 [kg];
            attribute :>> cost = 268.0;
            port supply : Common::PowerPort;
            part sensors : Sensor_0268[2];
            action smooth : Common::Process;
            action forward : Common::Process;
            succession first smooth then forward;
            exhibit state lifecycle : Common::Lifecycle;
        }
        requirement controllerMass_0268 : Common::MassLimit {
            subject component : Controller_0268;
            attribute :>> limit = 2.0 [kg];
        }
    }

    package Subsystem_0269 {
        part def Sensor_0269 :> Common::Component {
            attribute :>> mass = 0.24 [kg];
            attribute :>> cost = 39.0;
            attribute range : Real = 119.0;
            port data : Common::DataPort;
        }
        part def Controller_0269 :> Common::Component {
            attribute :>> mass = 1.30 [kg];
            attribute :>> cost = 269.0;
            port supply : Common::PowerPort;
            part sensors : Sensor_0269[2];
            action smooth : Common::Process;
            action forward : Common::Process;
            succession first smooth then forward;
            exhibit state lifecycle : Common::Lifecycle;
        }
        requirement controllerMass_0269 : Common::MassLimit {
            subject component : Controller_0269;
            attribute :>> limit = 2.0 [kg];
        }
    }

    package Subsystem_0270 {
        part def Sensor_0270 :> Common::Component {
            attribute :>> mass = 0.20 [kg];
            attribute :>> cost = 40.0;
            attribute range : Real = 120.0;
            port data : Common::DataPort;
        }
        part def Controller_0270 :> Common::Component {
            attribute :>> mass = 1.40 [kg];
            attribute :>> cost = 270.0;
            port supply : Common::PowerPort;
            part sensors : Sensor_0270[2];
            action smooth : Common::Process;
            action forward : Common::Process;
            succession first smooth then forward;
            exhibit state lifecycle : Common::Lifecycle;
        }
        requirement controllerMass_0270 : Common::MassLimit {
            subject component : Controller_0270;
            attribute :>> limit = 2.0 [kg];
        }
    }

    package Subsystem_0271 {
        part def Sensor_0271 :> Common::Component {
            attribute :>> mass = 0.21 [kg];
            attribute :>> cost = 41.0;
            attribute range : Real = 121.0;
            port data : Common::DataPort;
        }
        part def Controller_0271 :> Common::Component {
            attribute :>> mass = 1.50 [kg];
            attribute :>> cost = 271.0;
            port supply : Common::PowerPort;
            part sensors : Sensor_0271[2];
            action smooth : Common::Process;
            action forward : Common::Process;
            succession first smooth then forward;
            exhibit state lifecycle : Common::Lifecycle;
        }
        requirement controllerMass_0271 : Common::MassLimit {
            subject component : Controller_0271;
            attribute :>> limit = 2.0 [kg];
        }
    }

    package Subsystem_0272 {
        part def Sensor_0272 :> Common::Component {
            attribute :>> mass = 0.22 [kg];
            attribute :>> cost = 42.0;
            attribute range : Real = 122.0;
            port data : Common::DataPort;
        }
        part def Controller_0272 :> Common::Component {
            attribute :>> mass = 1.60 [kg];
            attribute :>> cost = 272.0;
            port supply : Common::PowerPort;
            part sensors : Sensor_0272[2];
            action smooth : Common::Process;
            action forward : Common::Process;
            succession first smooth then forward;
            exhibit state lifecycle : Common::Lifecycle;
        }
        requirement controllerMass_0272 : Common::MassLimit {
            subject component : Controller_0272;
            attribute :>> limit = 2.0 [kg];
        }
    }

    package Subsystem_0273 {
        part def Sensor_0273 :> Common::Component {
            attribute :>> mass = 0.23 [kg];
            attribute :>> cost = 43.0;
            attribute range : Real = 123.0;
            port data : Common::DataPort;
        }
        part def Controller_0273 :> Common::Component {
            attribute :>> mass = 1.00 [kg];
            attribute :>> cost = 273.0;
            port supply : Common::PowerPort;
            part sensors : Sensor_0273[2];
            action smooth : Common::Process;
            action forward : Common::Process;
            succession first smooth then forward;
            exhibit state lifecycle : Common::Lifecycle;
        }
        requirement controllerMass_0273 : Common::MassLimit {
            subject component : Controller_0273;
            attribute :>> limit = 2.0 [kg];
        }
    }

    package Subsystem_0274 {
        part def Sensor_0274 :> Common::Component {
            attribute :>> mass = 0.24 [kg];
            attribute :>> cost = 44.0;
            attribute range : Real = 124.0;
            port data : Common::DataPort;
        }
        part def Controller_0274 :> Common::Component {
            attribute :>> mass = 1.10 [kg];
            attribute :>> cost = 274.0;
            port supply : Common::PowerPort;
            part sensors : Sensor_0274[2];
            action smooth : Common::Process;
            action forward : Common::Process;
            succession first smooth then forward;
            exhibit state lifecycle : Common::Lifecycle;
        }
        requirement controllerMass_0274 : Common::MassLimit {
            subject component : Controller_0274;
            attribute :>> limit = 2.0 [kg];
        }
    }

    package Subsystem_0275 {
        part def Sensor_0275 :> Common::Component {
            attribute :>> mass = 0.20 [kg];
            attribute :>> cost = 45.0;
            attribute range : Real = 125.0;
            port data : Common::DataPort;
        }
        part def Controller_0275 :> Common::Component {
            attribute :>> mass = 1.20 [kg];
            attribute :>> cost = 275.0;
            port supply : Common::PowerPort;
            part sensors : Sensor_0275[2];
            action smooth : Common::Process;
            action forward : Common::Process;
            succession first smooth then forward;
            exhibit state lifecycle : Common::Lifecycle;
        }
        requirement controllerMass_0275 : Common::MassLimit {
            subject component : Controller_0275;
            attribute :>> limit = 2.0 [kg];
        }
    }

    package Subsystem_0276 {
        part def Sensor_0276 :> Common::Component {
            attribute :>> mass = 0.21 [kg];
            attribute :>> cost = 46.0;
            attribute range : Real = 126.0;
            port data : Common::DataPort;
        }
        part def Controller_0276 :> Common::Component {
            attribute :>> mass = 1.30 [kg];
            attribute :>> cost = 276.0;
            port supply : Common::PowerPort;
            part sensors : Sensor_0276[2];
            action smooth : Common::Process;
            action forward : Common::Process;
            succession first smooth then forward;
            exhibit state lifecycle : Common::Lifecycle;
        }
        requirement controllerMass_0276 : Common::MassLimit {
            subject component : Controller_0276;
            attribute :>> limit = 2.0 [kg];
        }
    }

    package Subsystem_0277 {
        part def Sensor_0277 :> Common::Component {
            attribute :>> mass = 0.22 [kg];
            attribute :>> cost = 47.0;
            attribute range : Real = 127.0;
            port data : Common::DataPort;
        }
        part def Controller_0277 :> Common::Component {
            attribute :>> mass = 1.40 [kg];
            attribute :>> cost = 277.0;
            port supply : Common::PowerPort;
            part sensors : Sensor_0277[2];
            action smooth : Common::Process;
            action forward : Common::Process;
            succession first smooth then forward;
            exhibit state lifecycle : Common::Lifecycle;
        }
        requirement controllerMass_0277 : Common::MassLimit {
            subject component : Controller_0277;
            attribute :>> limit = 2.0 [kg];
        }
    }

    package Subsystem_0278 {
        part def Sensor_0278 :> Common::Component {
            attribute :>> mass = 0.23 [kg];
            attribute :>> cost = 48.0;
            attribute range : Real = 128.0;
            port data : Common::DataPort;
        }
        part def Controller_0278 :> Common::Component {
            attribute :>> mass = 1.50 [kg];
            attribute :>> cost = 278.0;
            port supply : Common::PowerPort;
            part sensors : Sensor_0278[2];
            action smooth : Common::Process;
            action forward : Common::Process;
            succession first smooth then forward;
            exhibit state lifecycle : Common::Lifecycle;
        }
        requirement controllerMass_0278 : Common::MassLimit {
            subject component : Controller_0278;
            attribute :>> limit = 2.0 [kg];
        }
    }

    package Subsystem_0279 {
        part def Sensor_0279 :> Common::Component {
            attribute :>> mass = 0.24 [kg];
            attribute :>> cost = 49.0;
            attribute range : Real = 129.0;
            port data : Common::DataPort;
        }
        part def Controller_0279 :> Common::Component {
            attribute :>> mass = 1.60 [kg];
            attribute :>> cost = 279.0;
            port supply : Common::PowerPort;
            part sensors : Sensor_0279[2];
            action smooth : Common::Process;
            action forward : Common::Process;
            succession first smooth then forward;
            exhibit state lifecycle : Common::Lifecycle;
        }
        requirement controllerMass_0279 : Common::MassLimit {
            subject component : Controller_0279;
            attribute :>> limit = 2.0 [kg];
        }
    }

    package Subsystem_0280 {
        part def Sensor_0280 :> Common::Component {
            attribute :>> mass = 0.20 [kg];
            attribute :>> cost = 30.0;
            attribute range : Real = 130.0;
            port data : Common::DataPort;
        }
        part def Controller_0280 :> Common::Component {
            attribute :>> mass = 1.00 [kg];
            attribute :>> cost = 280.0;
            port supply : Common::PowerPort;
            part sensors : Sensor_0280[2];
            action smooth : Common::Process;
            action forward : Common::Process;
            succession first smooth then forward;
            exhibit state lifecycle : Common::Lifecycle;
        }
        requirement controllerMass_0280 : Common::MassLimit {
            subject component : Controller_0280;
            attribute :>> limit = 2.0 [kg];
        }
    }

    package Subsystem_0281 {
        part def Sensor_0281 :> Common::Component {
            attribute :>> mass = 0.21 [kg];
            attribute :>> cost = 31.0;
            attribute range : Real = 131.0;
            port data : Common::DataPort;
        }
        part def Controller_0281 :> Common::Component {
            attribute :>> mass = 1.10 [kg];
            attribute :>> cost = 281.0;
            port supply : Common::PowerPort;
            part sensors : Sensor_0281[2];
            action smooth : Common::Process;
            action forward : Common::Process;
            succession first smooth then forward;
            exhibit state lifecycle : Common::Lifecycle;
        }
        requirement controllerMass_0281 : Common::MassLimit {
            subject component : Controller_0281;
            attribute :>> limit = 2.0 [kg];
        }
    }

    package Subsystem_0282 {
        part def Sensor_0282 :> Common::Component {
            attribute :>> mass = 0.22 [kg];
            attribute :>> cost = 32.0;
            attribute range : Real = 132.0;
            port data : Common::DataPort;
        }
        part def Controller_0282 :> Common::Component {
            attribute :>> mass = 1.20 [kg];
            attribute :>> cost = 282.0;
            port supply : Common::PowerPort;
            part sensors : Sensor_0282[2];
            action smooth : Common::Process;
            action forward : Common::Process;
            succession first smooth then forward;
            exhibit state lifecycle : Common::Lifecycle;
        }
        requirement controllerMass_0282 : Common::MassLimit {
            subject component : Controller_0282;
            attribute :>> limit = 2.0 [kg];
        }
    }

    package Subsystem_0283 {
        part def Sensor_0283 :> Common::Component {
            attribute :>> mass = 0.23 [kg];
            attribute :>> cost = 33.0;
            attribute range : Real = 133.0;
            port data : Common::DataPort;
        }
        part def Controller_0283 :> Common::Component {
            attribute :>> mass = 1.30 [kg];
            attribute :>> cost = 283.0;
            port supply : Common::PowerPort;
            part sensors : Sensor_0283[2];
            action smooth : Common::Process;
            action forward : Common::Process;
            succession first smooth then forward;
            exhibit state lifecycle : Common::Lifecycle;
        }
        requirement controllerMass_0283 : Common::MassLimit {
            subject component : Controller_0283;
            attribute :>> limit = 2.0 [kg];
        }
    }

    package Subsystem_0284 {
        part def Sensor_0284 :> Common::Component {
            attribute :>> mass = 0.24 [kg];
            attribute :>> cost = 34.0;
            attribute range : Real = 134.0;
            port data : Common::DataPort;
        }
        part def Controller_0284 :> Common::Component {
            attribute :>> mass = 1.40 [kg];
            attribute :>> cost = 284.0;
            port supply : Common::PowerPort;
            part sensors : Sensor_0284[2];
            action smooth : Common::Process;
            action forward : Common::Process;
            succession first smooth then forward;
            exhibit state lifecycle : Common::Lifecycle;
        }
        requirement controllerMass_0284 : Common::MassLimit {
            subject component : Controller_0284;
            attribute :>> limit = 2.0 [kg];
        }
    }

    package Subsystem_0285 {
        part def Sensor_0285 :> Common::Component {
            attribute :>> mass = 0.20 [kg];
            attribute :>> cost = 35.0;
            attribute range : Real = 135.0;
            port data : Common::DataPort;
        }
        part def Controller_0285 :> Common::Component {
            attribute :>> mass = 1.50 [kg];
            attribute :>> cost = 285.0;
            port supply : Common::PowerPort;
            part sensors : Sensor_0285[2];
            action smooth : Common::Process;
            action forward : Common::Process;
            succession first smooth then forward;
            exhibit state lifecycle : Common::Lifecycle;
        }
        requirement controllerMass_0285 : Common::MassLimit {
            subject component : Controller_0285;
            attribute :>> limit = 2.0 [kg];
        }
    }

    package Subsystem_0286 {
        part def Sensor_0286 :> Common::Component {
            attribute :>> mass = 0.21 [kg];
            attribute :>> cost = 36.0;
            attribute range : Real = 136.0;
            port data : Common::DataPort;
        }
        part def Controller_0286 :> Common::Component {
            attribute :>> mass = 1.60 [kg];
            attribute :>> cost = 286.0;
            port supply : Common::PowerPort;
            part sensors : Sensor_0286[2];
            action smooth : Common::Process;
            action forward : Common::Process;
            succession first smooth then forward;
            exhibit state lifecycle : Common::Lifecycle;
        }
        requirement controllerMass_0286 : Common::MassLimit {
            subject component : Controller_0286;
            attribute :>> limit = 2.0 [kg];
        }
    }

    package Subsystem_0287 {
        part def Sensor_0287 :> Common::Component {
            attribute :>> mass = 0.22 [kg];
            attribute :>> cost = 37.0;
            attribute range : Real = 137.0;
            port data : Common::DataPort;
        }
        part def Controller_0287 :> Common::Component {
            attribute :>> mass = 1.00 [kg];
            attribute :>> cost = 287.0;
            port supply : Common::PowerPort;
            part sensors : Sensor_0287[2];
            action smooth : Common::Process;
            action forward : Common::Process;
            succession first smooth then forward;
            exhibit state lifecycle : Common::Lifecycle;
        }
        requirement controllerMass_0287 : Common::MassLimit {
            subject component : Controller_0287;
            attribute :>> limit = 2.0 [kg];
        }
    }

    package Subsystem_0288 {
        part def Sensor_0288 :> Common::Component {
            attribute :>> mass = 0.23 [kg];
            attribute :>> cost = 38.0;
            attribute range : Real = 138.0;
            port data : Common::DataPort;
        }
        part def Controller_0288 :> Common::Component {
            attribute :>> mass = 1.10 [kg];
            attribute :>> cost = 288.0;
            port supply : Common::PowerPort;
            part sensors : Sensor_0288[2];
            action smooth : Common::Process;
            action forward : Common::Process;
            succession first smooth then forward;
            exhibit state lifecycle : Common::Lifecycle;
        }
        requirement controllerMass_0288 : Common::MassLimit {
            subject component : Controller_0288;
            attribute :>> limit = 2.0 [kg];
        }
    }

    package Subsystem_0289 {
        part def Sensor_0289 :> Common::Component {
            attribute :>> mass = 0.24 [kg];
            attribute :>> cost = 39.0;
            attribute range : Real = 139.0;
            port data : Common::DataPort;
        }
        part def Controller_0289 :> Common::Component {
            attribute :>> mass = 1.20 [kg];
            attribute :>> cost = 289.0;
            port supply : Common::PowerPort;
            part sensors : Sensor_0289[2];
            action smooth : Common::Process;
            action forward : Common::Process;
            succession first smooth then forward;
            exhibit state lifecycle : Common::Lifecycle;
        }
        requirement controllerMass_0289 : Common::MassLimit {
            subject component : Controller_0289;
            attribute :>> limit = 2.0 [kg];
        }
    }

    package Subsystem_0290 {
        part def Sensor_0290 :> Common::Component {
            attribute :>> mass = 0.20 [kg];
            attribute :>> cost = 40.0;
            attribute range : Real = 140.0;
            port data : Common::DataPort;
        }
        part def Controller_0290 :> Common::Component {
            attribute :>> mass = 1.30 [kg];
            attribute :>> cost = 290.0;
            port supply : Common::PowerPort;
            part sensors : Sensor_0290[2];
            action smooth : Common::Process;
            action forward : Common::Process;
            succession first smooth then forward;
            exhibit state lifecycle : Common::Lifecycle;
        }
        requirement controllerMass_0290 : Common::MassLimit {
            subject component : Controller_0290;
            attribute :>> limit = 2.0 [kg];
        }
    }

    package Subsystem_0291 {
        part def Sensor_0291 :> Common::Component {
            attribute :>> mass = 0.21 [kg];
            attribute :>> cost = 41.0;
            attribute range : Real = 141.0;
            port data : Common::DataPort;
        }
        part def Controller_0291 :> Common::Component {
            attribute :>> mass = 1.40 [kg];
            attribute :>> cost = 291.0;
            port supply : Common::PowerPort;
            part sensors : Sensor_0291[2];
            action smooth : Common::Process;
            action forward : Common::Process;
            succession first smooth then forward;
            exhibit state lifecycle : Common::Lifecycle;
        }
        requirement controllerMass_0291 : Common::MassLimit {
            subject component : Controller_0291;
            attribute :>> limit = 2.0 [kg];
        }
    }

    package Subsystem_0292 {
        part def Sensor_0292 :> Common::Component {
            attribute :>> mass = 0.22 [kg];
            attribute :>> cost = 42.0;
            attribute range : Real = 142.0;
            port data : Common::DataPort;
        }
        part def Controller_0292 :> Common::Component {
            attribute :>> mass = 1.50 [kg];
            attribute :>> cost = 292.0;
            port supply : Common::PowerPort;
            part sensors : Sensor_0292[2];
            action smooth : Common::Process;
            action forward : Common::Process;
            succession first smooth then forward;
            exhibit state lifecycle : Common::Lifecycle;
        }
        requirement controllerMass_0292 : Common::MassLimit {
            subject component : Controller_0292;
            attribute :>> limit = 2.0 [kg];
        }
    }

    package Subsystem_0293 {
        part def Sensor_0293 :> Common::Component {
            attribute :>> mass = 0.23 [kg];
            attribute :>> cost = 43.0;
            attribute range : Real = 143.0;
            port data : Common::DataPort;
        }
        part def Controller_0293 :> Common::Component {
            attribute :>> mass = 1.60 [kg];
            attribute :>> cost = 293.0;
            port supply : Common::PowerPort;
            part sensors : Sensor_0293[2];
            action smooth : Common::Process;
            action forward : Common::Process;
            succession first smooth then forward;
            exhibit state lifecycle : Common::Lifecycle;
        }
        requirement controllerMass_0293 : Common::MassLimit {
            subject component : Controller_0293;
            attribute :>> limit = 2.0 [kg];
        }
    }

    package Subsystem_0294 {
        part def Sensor_0294 :> Common::Component {
            attribute :>> mass = 0.24 [kg];
            attribute :>> cost = 44.0;
            attribute range : Real = 144.0;
            port data : Common::DataPort;
        }
        part def Controller_0294 :> Common::Component {
            attribute :>> mass = 1.00 [kg];
            attribute :>> cost = 294.0;
            port supply : Common::PowerPort;
            part sensors : Sensor_0294[2];
            action smooth : Common::Process;
            action forward : Common::Process;
            succession first smooth then forward;
            exhibit state lifecycle : Common::Lifecycle;
        }
        requirement controllerMass_0294 : Common::MassLimit {
            subject component : Controller_0294;
            attribute :>> limit = 2.0 [kg];
        }
    }

    package Subsystem_0295 {
        part def Sensor_0295 :> Common::Component {
            attribute :>> mass = 0.20 [kg];
            attribute :>> cost = 45.0;
            attribute range : Real = 145.0;
            port data : Common::DataPort;
        }
        part def Controller_0295 :> Common::Component {
            attribute :>> mass = 1.10 [kg];
            attribute :>> cost = 295.0;
            port supply : Common::PowerPort;
            part sensors : Sensor_0295[2];
            action smooth : Common::Process;
            action forward : Common::Process;
            succession first smooth then forward;
            exhibit state lifecycle : Common::Lifecycle;
        }
        requirement controllerMass_0295 : Common::MassLimit {
            subject component : Controller_0295;
            attribute :>> limit = 2.0 [kg];
        }
    }

    package Subsystem_0296 {
        part def Sensor_0296 :> Common::Component {
            attribute :>> mass = 0.21 [kg];
            attribute :>> cost = 46.0;
            attribute range : Real = 146.0;
            port data : Common::DataPort;
        }
        part def Controller_0296 :> Common::Component {
            attribute :>> mass = 1.20 [kg];
            attribute :>> cost = 296.0;
            port supply : Common::PowerPort;
            part sensors : Sensor_0296[2];
            action smooth : Common::Process;
            action forward : Common::Process;
            succession first smooth then forward;
            exhibit state lifecycle : Common::Lifecycle;
        }
        requirement controllerMass_0296 : Common::MassLimit {
            subject component : Controller_0296;
            attribute :>> limit = 2.0 [kg];
        }
    }

    package Subsystem_0297 {
        part def Sensor_0297 :> Common::Component {
            attribute :>> mass = 0.22 [kg];
            attribute :>> cost = 47.0;
            attribute range : Real = 147.0;
            port data : Common::DataPort;
        }
        part def Controller_0297 :> Common::Component {
            attribute :>> mass = 1.30 [kg];
            attribute :>> cost = 297.0;
            port supply : Common::PowerPort;
            part sensors : Sensor_0297[2];
            action smooth : Common::Process;
            action forward : Common::Process;
            succession first smooth then forward;
            exhibit state lifecycle : Common::Lifecycle;
        }
        requirement controllerMass_0297 : Common::MassLimit {
            subject component : Controller_0297;
            attribute :>> limit = 2.0 [kg];
        }
    }

    package Subsystem_0298 {
        part def Sensor_0298 :> Common::Component {
            attribute :>> mass = 0.23 [kg];
            attribute :>> cost = 48.0;
            attribute range : Real = 148.0;
            port data : Common::DataPort;
        }
        part def Controller_0298 :> Common::Component {
            attribute :>> mass = 1.40 [kg];
            attribute :>> cost = 298.0;
            port supply : Common::PowerPort;
            part sensors : Sensor_0298[2];
            action smooth : Common::Process;
            action forward : Common::Process;
            succession first smooth then forward;
            exhibit state lifecycle : Common::Lifecycle;
        }
        requirement controllerMass_0298 : Common::MassLimit {
            subject component : Controller_0298;
            attribute :>> limit = 2.0 [kg];
        }
    }

    package Subsystem_0299 {
        part def Sensor_0299 :> Common::Component {
            attribute :>> mass = 0.24 [kg];
            attribute :>> cost = 49.0;
            attribute range : Real = 149.0;
            port data : Common::DataPort;
        }
        part def Controller_0299 :> Common::Component {
            attribute :>> mass = 1.50 [kg];
            attribute :>> cost = 299.0;
            port supply : Common::PowerPort;
            part sensors : Sensor_0299[2];
            action smooth : Common::Process;
            action forward : Common::Process;
            succession first smooth then forward;
            exhibit state lifecycle : Common::Lifecycle;
        }
        requirement controllerMass_0299 : Common::MassLimit {
            subject component : Controller_0299;
            attribute :>> limit = 2.0 [kg];
        }
    }

    package Subsystem_0300 {
        part def Sensor_0300 :> Common::Component {
            attribute :>> mass = 0.20 [kg];
            attribute :>> cost = 30.0;
            attribute range : Real = 100.0;
            port data : Common::DataPort;
        }
        part def Controller_0300 :> Common::Component {
            attribute :>> mass = 1.60 [kg];
            attribute :>> cost = 200.0;
            port supply : Common::PowerPort;
            part sensors : Sensor_0300[2];
            action smooth : Common::Process;
            action forward : Common::Process;
            succession first smooth then forward;
            exhibit state lifecycle : Common::Lifecycle;
        }
        requirement controllerMass_0300 : Common::MassLimit {
            subject component : Controller_0300;
            attribute :>> limit = 2.0 [kg];
        }
    }

    package Subsystem_0301 {
        part def Sensor_0301 :> Common::Component {
            attribute :>> mass = 0.21 [kg];
            attribute :>> cost = 31.0;
            attribute range : Real = 101.0;
            port data : Common::DataPort;
        }
        part def Controller_0301 :> Common::Component {
            attribute :>> mass = 1.00 [kg];
            attribute :>> cost = 201.0;
            port supply : Common::PowerPort;
            part sensors : Sensor_0301[2];
            action smooth : Common::Process;
            action forward : Common::Process;
            succession first smooth then forward;
            exhibit state lifecycle : Common::Lifecycle;
        }
        requirement controllerMass_0301 : Common::MassLimit {
            subject component : Controller_0301;
            attribute :>> limit = 2.0 [kg];
        }
    }

    package Subsystem_0302 {
        part def Sensor_0302 :> Common::Component {
            attribute :>> mass = 0.22 [kg];
            attribute :>> cost = 32.0;
            attribute range : Real = 102.0;
            port data : Common::DataPort;
        }
        part def Controller_0302 :> Common::Component {
            attribute :>> mass = 1.10 [kg];
            attribute :>> cost = 202.0;
            port supply : Common::PowerPort;
            part sensors : Sensor_0302[2];
            action smooth : Common::Process;
            action forward : Common::Process;
            succession first smooth then forward;
            exhibit state lifecycle : Common::Lifecycle;
        }
        requirement controllerMass_0302 : Common::MassLimit {
            subject component : Controller_0302;
            attribute :>> limit = 2.0 [kg];
        }
    }

    package Subsystem_0303 {
        part def Sensor_0303 :> Common::Component {
            attribute :>> mass = 0.23 [kg];
            attribute :>> cost = 33.0;
            attribute range : Real = 103.0;
            port data : Common::DataPort;
        }
        part def Controller_0303 :> Common::Component {
            attribute :>> mass = 1.20 [kg];
            attribute :>> cost = 203.0;
            port supply : Common::PowerPort;
            part sensors : Sensor_0303[2];
            action smooth : Common::Process;
            action forward : Common::Process;
            succession first smooth then forward;
            exhibit state lifecycle : Common::Lifecycle;
        }
        requirement controllerMass_0303 : Common::MassLimit {
            subject component : Controller_0303;
            attribute :>> limit = 2.0 [kg];
        }
    }

    package Subsystem_0304 {
        part def Sensor_0304 :> Common::Component {
            attribute :>> mass = 0.24 [kg];
            attribute :>> cost = 34.0;
            attribute range : Real = 104.0;
            port data : Common::DataPort;
        }
        part def Controller_0304 :> Common::Component {
            attribute :>> mass = 1.30 [kg];
            attribute :>> cost = 204.0;
            port supply : Common::PowerPort;
            part sensors : Sensor_0304[2];
            action smooth : Common::Process;
            action forward : Common::Process;
            succession first smooth then forward;
            exhibit state lifecycle : Common::Lifecycle;
        }
        requirement controllerMass_0304 : Common::MassLimit {
            subject component : Controller_0304;
            attribute :>> limit = 2.0 [kg];
        }
    }

    package Subsystem_0305 {
        part def Sensor_0305 :> Common::Component {
            attribute :>> mass = 0.20 [kg];
            attribute :>> cost = 35.0;
            attribute range : Real = 105.0;
            port data : Common::DataPort;
        }
        part def Controller_0305 :> Common::Component {
            attribute :>> mass = 1.40 [kg];
            attribute :>> cost = 205.0;
            port supply : Common::PowerPort;
            part sensors : Sensor_0305[2];
            action smooth : Common::Process;
            action forward : Common::Process;
            succession first smooth then forward;
            exhibit state lifecycle : Common::Lifecycle;
        }
        requirement controllerMass_0305 : Common::MassLimit {
            subject component : Controller_0305;
            attribute :>> limit = 2.0 [kg];
        }
    }

    package Subsystem_0306 {
        part def Sensor_0306 :> Common::Component {
            attribute :>> mass = 0.21 [kg];
            attribute :>> cost = 36.0;
            attribute range : Real = 106.0;
            port data : Common::DataPort;
        }
        part def Controller_0306 :> Common::Component {
            attribute :>> mass = 1.50 [kg];
            attribute :>> cost = 206.0;
            port supply : Common::PowerPort;
            part sensors : Sensor_0306[2];
            action smooth : Common::Process;
            action forward : Common::Process;
            succession first smooth then forward;
            exhibit state lifecycle : Common::Lifecycle;
        }
        requirement controllerMass_0306 : Common::MassLimit {
            subject component : Controller_0306;
            attribute :>> limit = 2.0 [kg];
        }
    }

    package Subsystem_0307 {
        part def Sensor_0307 :> Common::Component {
            attribute :>> mass = 0.22 [kg];
            attribute :>> cost = 37.0;
            attribute range : Real = 107.0;
            port data : Common::DataPort;
        }
        part def Controller_0307 :> Common::Component {
            attribute :>> mass = 1.60 [kg];
            attribute :>> cost = 207.0;
            port supply : Common::PowerPort;
            part sensors : Sensor_0307[2];
            action smooth : Common::Process;
            action forward : Common::Process;
            succession first smooth then forward;
            exhibit state lifecycle : Common::Lifecycle;
        }
        requirement controllerMass_0307 : Common::MassLimit {
            subject component : Controller_0307;
            attribute :>> limit = 2.0 [kg];
        }
    }

    package Subsystem_0308 {
        part def Sensor_0308 :> Common::Component {
            attribute :>> mass = 0.23 [kg];
            attribute :>> cost = 38.0;
            attribute range : Real = 108.0;
            port data : Common::DataPort;
        }
        part def Controller_0308 :> Common::Component {
            attribute :>> mass = 1.00 [kg];
            attribute :>> cost = 208.0;
            port supply : Common::PowerPort;
            part sensors : Sensor_0308[2];
            action smooth : Common::Process;
            action forward : Common::Process;
            succession first smooth then forward;
            exhibit state lifecycle : Common::Lifecycle;
        }
        requirement controllerMass_0308 : Common::MassLimit {
            subject component : Controller_0308;
            attribute :>> limit = 2.0 [kg];
        }
    }

    package Subsystem_0309 {
        part def Sensor_0309 :> Common::Component {
            attribute :>> mass = 0.24 [kg];
            attribute :>> cost = 39.0;
            attribute range : Real = 109.0;
            port data : Common::DataPort;
        }
        part def Controller_0309 :> Common::Component {
            attribute :>> mass = 1.10 [kg];
            attribute :>> cost = 209.0;
            port supply : Common::PowerPort;
            part sensors : Sensor_0309[2];
            action smooth : Common::Process;
            action forward : Common::Process;
            succession first smooth then forward;
            exhibit state lifecycle : Common::Lifecycle;
        }
        requirement controllerMass_0309 : Common::MassLimit {
            subject component : Controller_0309;
            attribute :>> limit = 2.0 [kg];
        }
    }

    package Subsystem_0310 {
        part def Sensor_0310 :> Common::Component {
            attribute :>> mass = 0.20 [kg];
            attribute :>> cost = 40.0;
            attribute range : Real = 110.0;
            port data : Common::DataPort;
        }
        part def Controller_0310 :> Common::Component {
            attribute :>> mass = 1.20 [kg];
            attribute :>> cost = 210.0;
            port supply : Common::PowerPort;
            part sensors : Sensor_0310[2];
            action smooth : Common::Process;
            action forward : Common::Process;
            succession first smooth then forward;
            exhibit state lifecycle : Common::Lifecycle;
        }
        requirement controllerMass_0310 : Common::MassLimit {
            subject component : Controller_0310;
            attribute :>> limit = 2.0 [kg];
        }
    }

    package Subsystem_0311 {
        part def Sensor_0311 :> Common::Component {
            attribute :>> mass = 0.21 [kg];
            attribute :>> cost = 41.0;
            attribute range : Real = 111.0;
            port data : Common::DataPort;
        }
        part def Controller_0311 :> Common::Component {
            attribute :>> mass = 1.30 [kg];
            attribute :>> cost = 211.0;
            port supply : Common::PowerPort;
            part sensors : Sensor_0311[2];
            action smooth : Common::Process;
            action forward : Common::Process;
            succession first smooth then forward;
            exhibit state lifecycle : Common::Lifecycle;
        }
        requirement controllerMass_0311 : Common::MassLimit {
            subject component : Controller_0311;
            attribute :>> limit = 2.0 [kg];
        }
    }

    package Subsystem_0312 {
        part def Sensor_0312 :> Common::Component {
            attribute :>> mass = 0.22 [kg];
            attribute :>> cost = 42.0;
            attribute range : Real = 112.0;
            port data : Common::DataPort;
        }
        part def Controller_0312 :> Common::Component {
            attribute :>> mass = 1.40 [kg];
            attribute :>> cost = 212.0;
            port supply : Common::PowerPort;
            part sensors : Sensor_0312[2];
            action smooth : Common::Process;
            action forward : Common::Process;
            succession first smooth then forward;
            exhibit state lifecycle : Common::Lifecycle;
        }
        requirement controllerMass_0312 : Common::MassLimit {
            subject component : Controller_0312;
            attribute :>> limit = 2.0 [kg];
        }
    }

    package Subsystem_0313 {
        part def Sensor_0313 :> Common::Component {
            attribute :>> mass = 0.23 [kg];
            attribute :>> cost = 43.0;
            attribute range : Real = 113.0;
            port data : Common::DataPort;
        }
        part def Controller_0313 :> Common::Component {
            attribute :>> mass = 1.50 [kg];
            attribute :>> cost = 213.0;
            port supply : Common::PowerPort;
            part sensors : Sensor_0313[2];
            action smooth : Common::Process;
            action forward : Common::Process;
            succession first smooth then forward;
            exhibit state lifecycle : Common::Lifecycle;
        }
        requirement controllerMass_0313 : Common::MassLimit {
            subject component : Controller_0313;
            attribute :>> limit = 2.0 [kg];
        }
    }

    package Subsystem_0314 {
        part def Sensor_0314 :> Common::Component {
            attribute :>> mass = 0.24 [kg];
            attribute :>> cost = 44.0;
            attribute range : Real = 114.0;
            port data : Common::DataPort;
        }
        part def Controller_0314 :> Common::Component {
            attribute :>> mass = 1.60 [kg];
            attribute :>> cost = 214.0;
            port supply : Common::PowerPort;
            part sensors : Sensor_0314[2];
            action smooth : Common::Process;
            action forward : Common::Process;
            succession first smooth then forward;
            exhibit state lifecycle : Common::Lifecycle;
        }
        requirement controllerMass_0314 : Common::MassLimit {
            subject component : Controller_0314;
            attribute :>> limit = 2.0 [kg];
        }
    }

    package Subsystem_0315 {
        part def Sensor_0315 :> Common::Component {
            attribute :>> mass = 0.20 [kg];
            attribute :>> cost = 45.0;
            attribute range : Real = 115.0;
            port data : Common::DataPort;
        }
        part def Controller_0315 :> Common::Component {
            attribute :>> mass = 1.00 [kg];
            attribute :>> cost = 215.0;
            port supply : Common::PowerPort;
            part sensors : Sensor_0315[2];
            action smooth : Common::Process;
            action forward : Common::Process;
            succession first smooth then forward;
            exhibit state lifecycle : Common::Lifecycle;
        }
        requirement controllerMass_0315 : Common::MassLimit {
            subject component : Controller_0315;
            attribute :>> limit = 2.0 [kg];
        }
    }

    package Subsystem_0316 {
        part def Sensor_0316 :> Common::Component {
            attribute :>> mass = 0.21 [kg];
            attribute :>> cost = 46.0;
            attribute range : Real = 116.0;
            port data : Common::DataPort;
        }
        part def Controller_0316 :> Common::Component {
            attribute :>> mass = 1.10 [kg];
            attribute :>> cost = 216.0;
            port supply : Common::PowerPort;
            part sensors : Sensor_0316[2];
            action smooth : Common::Process;
            action forward : Common::Process;
            succession first smooth then forward;
            exhibit state lifecycle : Common::Lifecycle;
        }
        requirement controllerMass_0316 : Common::MassLimit {
            subject component : Controller_0316;
            attribute :>> limit = 2.0 [kg];
        }
    }

    package Subsystem_0317 {
        part def Sensor_0317 :> Common::Component {
            attribute :>> mass = 0.22 [kg];
            attribute :>> cost = 47.0;
            attribute range : Real = 117.0;
            port data : Common::DataPort;
        }
        part def Controller_0317 :> Common::Component {
            attribute :>> mass = 1.20 [kg];
            attribute :>> cost = 217.0;
            port supply : Common::PowerPort;
            part sensors : Sensor_0317[2];
            action smooth : Common::Process;
            action forward : Common::Process;
            succession first smooth then forward;
            exhibit state lifecycle : Common::Lifecycle;
        }
        requirement controllerMass_0317 : Common::MassLimit {
            subject component : Controller_0317;
            attribute :>> limit = 2.0 [kg];
        }
    }

    package Subsystem_0318 {
        part def Sensor_0318 :> Common::Component {
            attribute :>> mass = 0.23 [kg];
            attribute :>> cost = 48.0;
            attribute range : Real = 118.0;
            port data : Common::DataPort;
        }
        part def Controller_0318 :> Common::Component {
            attribute :>> mass = 1.30 [kg];
            attribute :>> cost = 218.0;
            port supply : Common::PowerPort;
            part sensors : Sensor_0318[2];
            action smooth : Common::Process;
            action forward : Common::Process;
            succession first smooth then forward;
            exhibit state lifecycle : Common::Lifecycle;
        }
        requirement controllerMass_0318 : Common::MassLimit {
            subject component : Controller_0318;
            attribute :>> limit = 2.0 [kg];
        }
    }

    package Subsystem_0319 {
        part def Sensor_0319 :> Common::Component {
            attribute :>> mass = 0.24 [kg];
            attribute :>> cost = 49.0;
            attribute range : Real = 119.0;
            port data : Common::DataPort;
        }
        part def Controller_0319 :> Common::Component {
            attribute :>> mass = 1.40 [kg];
            attribute :>> cost = 219.0;
            port supply : Common::PowerPort;
            part sensors : Sensor_0319[2];
            action smooth : Common::Process;
            action forward : Common::Process;
            succession first smooth then forward;
            exhibit state lifecycle : Common::Lifecycle;
        }
        requirement controllerMass_0319 : Common::MassLimit {
            subject component : Controller_0319;
            attribute :>> limit = 2.0 [kg];
        }
    }

    package Subsystem_0320 {
        part def Sensor_0320 :> Common::Component {
            attribute :>> mass = 0.20 [kg];
            attribute :>> cost = 30.0;
            attribute range : Real = 120.0;
            port data : Common::DataPort;
        }
        part def Controller_0320 :> Common::Component {
            attribute :>> mass = 1.50 [kg];
            attribute :>> cost = 220.0;
            port supply : Common::PowerPort;
            part sensors : Sensor_0320[2];
            action smooth : Common::Process;
            action forward : Common::Process;
            succession first smooth then forward;
            exhibit state lifecycle : Common::Lifecycle;
        }
        requirement controllerMass_0320 : Common::MassLimit {
            subject component : Controller_0320;
            attribute :>> limit = 2.0 [kg];
        }
    }

    package Subsystem_0321 {
        part def Sensor_0321 :> Common::Component {
            attribute :>> mass = 0.21 [kg];
            attribute :>> cost = 31.0;
            attribute range : Real = 121.0;
            port data : Common::DataPort;
        }
        part def Controller_0321 :> Common::Component {
            attribute :>> mass = 1.60 [kg];
            attribute :>> cost = 221.0;
            port supply : Common::PowerPort;
            part sensors : Sensor_0321[2];
            action smooth : Common::Process;
            action forward : Common::Process;
            succession first smooth then forward;
            exhibit state lifecycle : Common::Lifecycle;
        }
        requirement controllerMass_0321 : Common::MassLimit {
            subject component : Controller_0321;
            attribute :>> limit = 2.0 [kg];
        }
    }

    package Subsystem_0322 {
        part def Sensor_0322 :> Common::Component {
            attribute :>> mass = 0.22 [kg];
            attribute :>> cost = 32.0;
            attribute range : Real = 122.0;
            port data : Common::DataPort;
        }
        part def Controller_0322 :> Common::Component {
            attribute :>> mass = 1.00 [kg];
            attribute :>> cost = 222.0;
            port supply : Common::PowerPort;
            part sensors : Sensor_0322[2];
            action smooth : Common::Process;
            action forward : Common::Process;
            succession first smooth then forward;
            exhibit state lifecycle : Common::Lifecycle;
        }
        requirement controllerMass_0322 : Common::MassLimit {
            subject component : Controller_0322;
            attribute :>> limit = 2.0 [kg];
        }
    }

    package Subsystem_0323 {
        part def Sensor_0323 :> Common::Component {
            attribute :>> mass = 0.23 [kg];
            attribute :>> cost = 33.0;
            attribute range : Real = 123.0;
            port data : Common::DataPort;
        }
        part def Controller_0323 :> Common::Component {
            attribute :>> mass = 1.10 [kg];
            attribute :>> cost = 223.0;
            port supply : Common::PowerPort;
            part sensors : Sensor_0323[2];
            action smooth : Common::Process;
            action forward : Common::Process;
            succession first smooth then forward;
            exhibit state lifecycle : Common::Lifecycle;
        }
        requirement controllerMass_0323 : Common::MassLimit {
            subject component : Controller_0323;
            attribute :>> limit = 2.0 [kg];
        }
    }

    package Subsystem_0324 {
        part def Sensor_0324 :> Common::Component {
            attribute :>> mass = 0.24 [kg];
            attribute :>> cost = 34.0;
            attribute range : Real = 124.0;
            port data : Common::DataPort;
        }
        part def Controller_0324 :> Common::Component {
            attribute :>> mass = 1.20 [kg];
            attribute :>> cost = 224.0;
            port supply : Common::PowerPort;
            part sensors : Sensor_0324[2];
            action smooth : Common::Process;
            action forward : Common::Process;
            succession first smooth then forward;
            exhibit state lifecycle : Common::Lifecycle;
        }
        requirement controllerMass_0324 : Common::MassLimit {
            subject component : Controller_0324;
            attribute :>> limit = 2.0 [kg];
        }
    }

    package Subsystem_0325 {
        part def Sensor_0325 :> Common::Component {
            attribute :>> mass = 0.20 [kg];
            attribute :>> cost = 35.0;
            attribute range : Real = 125.0;
            port data : Common::DataPort;
        }
        part def Controller_0325 :> Common::Component {
            attribute :>> mass = 1.30 [kg];
            attribute :>> cost = 225.0;
            port supply : Common::PowerPort;
            part sensors : Sensor_0325[2];
            action smooth : Common::Process;
            action forward : Common::Process;
            succession first smooth then forward;
            exhibit state lifecycle : Common::Lifecycle;
        }
        requirement controllerMass_0325 : Common::MassLimit {
            subject component : Controller_0325;
            attribute :>> limit = 2.0 [kg];
        }
    }

    package Subsystem_0326 {
        part def Sensor_0326 :> Common::Component {
            attribute :>> mass = 0.21 [kg];
            attribute :>> cost = 36.0;
            attribute range : Real = 126.0;
            port data : Common::DataPort;
        }
        part def Controller_0326 :> Common::Component {
            attribute :>> mass = 1.40 [kg];
            attribute :>> cost = 226.0;
            port supply : Common::PowerPort;
            part sensors : Sensor_0326[2];
            action smooth : Common::Process;
            action forward : Common::Process;
            succession first smooth then forward;
            exhibit state lifecycle : Common::Lifecycle;
        }
        requirement controllerMass_0326 : Common::MassLimit {
            subject component : Controller_0326;
            attribute :>> limit = 2.0 [kg];
        }
    }

    package Subsystem_0327 {
        part def Sensor_0327 :> Common::Component {
            attribute :>> mass = 0.22 [kg];
            attribute :>> cost = 37.0;
            attribute range : Real = 127.0;
            port data : Common::DataPort;
        }
        part def Controller_0327 :> Common::Component {
            attribute :>> mass = 1.50 [kg];
            attribute :>> cost = 227.0;
            port supply : Common::PowerPort;
            part sensors : Sensor_0327[2];
            action smooth : Common::Process;
            action forward : Common::Process;
            succession first smooth then forward;
            exhibit state lifecycle : Common::Lifecycle;
        }
        requirement controllerMass_0327 : Common::MassLimit {
            subject component : Controller_0327;
            attribute :>> limit = 2.0 [kg];
        }
    }

    package Subsystem_0328 {
        part def Sensor_0328 :> Common::Component {
            attribute :>> mass = 0.23 [kg];
            attribute :>> cost = 38.0;
            attribute range : Real = 128.0;
            port data : Common::DataPort;
        }
        part def Controller_0328 :> Common::Component {
            attribute :>> mass = 1.60 [kg];
            attribute :>> cost = 228.0;
            port supply : Common::PowerPort;
            part sensors : Sensor_0328[2];
            action smooth : Common::Process;
            action forward : Common::Process;
            succession first smooth then forward;
            exhibit state lifecycle : Common::Lifecycle;
        }
        requirement controllerMass_0328 : Common::MassLimit {
            subject component : Controller_0328;
            attribute :>> limit = 2.0 [kg];
        }
    }

    package Subsystem_0329 {
        part def Sensor_0329 :> Common::Component {
            attribute :>> mass = 0.24 [kg];
            attribute :>> cost = 39.0;
            attribute range : Real = 129.0;
            port data : Common::DataPort;
        }
        part def Controller_0329 :> Common::Component {
            attribute :>> mass = 1.00 [kg];
            attribute :>> cost = 229.0;
            port supply : Common::PowerPort;
            part sensors : Sensor_0329[2];
            action smooth : Common::Process;
            action forward : Common::Process;
            succession first smooth then forward;
            exhibit state lifecycle : Common::Lifecycle;
        }
        requirement controllerMass_0329 : Common::MassLimit {
            subject component : Controller_0329;
            attribute :>> limit = 2.0 [kg];
        }
    }

    package Subsystem_0330 {
        part def Sensor_0330 :> Common::Component {
            attribute :>> mass = 0.20 [kg];
            attribute :>> cost = 40.0;
            attribute range : Real = 130.0;
            port data : Common::DataPort;
        }
        part def Controller_0330 :> Common::Component {
            attribute :>> mass = 1.10 [kg];
            attribute :>> cost = 230.0;
            port supply : Common::PowerPort;
            part sensors : Sensor_0330[2];
            action smooth : Common::Process;
            action forward : Common::Process;
            succession first smooth then forward;
            exhibit state lifecycle : Common::Lifecycle;
        }
        requirement controllerMass_0330 : Common::MassLimit {
            subject component : Controller_0330;
            attribute :>> limit = 2.0 [kg];
        }
    }

    package Subsystem_0331 {
        part def Sensor_0331 :> Common::Component {
            attribute :>> mass = 0.21 [kg];
            attribute :>> cost = 41.0;
            attribute range : Real = 131.0;
            port data : Common::DataPort;
        }
        part def Controller_0331 :> Common::Component {
            attribute :>> mass = 1.20 [kg];
            attribute :>> cost = 231.0;
            port supply : Common::PowerPort;
            part sensors : Sensor_0331[2];
            action smooth : Common::Process;
            action forward : Common::Process;
            succession first smooth then forward;
            exhibit state lifecycle : Common::Lifecycle;
        }
        requirement controllerMass_0331 : Common::MassLimit {
            subject component : Controller_0331;
            attribute :>> limit = 2.0 [kg];
        }
    }

    package Subsystem_0332 {
        part def Sensor_0332 :> Common::Component {
            attribute :>> mass = 0.22 [kg];
            attribute :>> cost = 42.0;
            attribute range : Real = 132.0;
            port data : Common::DataPort;
        }
        part def Controller_0332 :> Common::Component {
            attribute :>> mass = 1.30 [kg];
            attribute :>> cost = 232.0;
            port supply : Common::PowerPort;
            part sensors : Sensor_0332[2];
            action smooth : Common::Process;
            action forward : Common::Process;
            succession first smooth then forward;
            exhibit state lifecycle : Common::Lifecycle;
        }
        requirement controllerMass_0332 : Common::MassLimit {
            subject component : Controller_0332;
            attribute :>> limit = 2.0 [kg];
        }
    }

    package Subsystem_0333 {
        part def Sensor_0333 :> Common::Component {
            attribute :>> mass = 0.23 [kg];
            attribute :>> cost = 43.0;
            attribute range : Real = 133.0;
            port data : Common::DataPort;
        }
        part def Controller_0333 :> Common::Component {
            attribute :>> mass = 1.40 [kg];
            attribute :>> cost = 233.0;
            port supply : Common::PowerPort;
            part sensors : Sensor_0333[2];
            action smooth : Common::Process;
            action forward : Common::Process;
            succession first smooth then forward;
            exhibit state lifecycle : Common::Lifecycle;
        }
        requirement controllerMass_0333 : Common::MassLimit {
            subject component : Controller_0333;
            attribute :>> limit = 2.0 [kg];
        }
    }

    package Subsystem_0334 {
        part def Sensor_0334 :> Common::Component {
            attribute :>> mass = 0.24 [kg];
            attribute :>> cost = 44.0;
            attribute range : Real = 134.0;
            port data : Common::DataPort;
        }
        part def Controller_0334 :> Common::Component {
            attribute :>> mass = 1.50 [kg];
            attribute :>> cost = 234.0;
            port supply : Common::PowerPort;
            part sensors : Sensor_0334[2];
            action smooth : Common::Process;
            action forward : Common::Process;
            succession first smooth then forward;
            exhibit state lifecycle : Common::Lifecycle;
        }
        requirement controllerMass_0334 : Common::MassLimit {
            subject component : Controller_0334;
            attribute :>> limit = 2.0 [kg];
        }
    }

    package Subsystem_0335 {
        part def Sensor_0335 :> Common::Component {
            attribute :>> mass = 0.20 [kg];
            attribute :>> cost = 45.0;
            attribute range : Real = 135.0;
            port data : Common::DataPort;
        }
        part def Controller_0335 :> Common::Component {
            attribute :>> mass = 1.60 [kg];
            attribute :>> cost = 235.0;
            port supply : Common::PowerPort;
            part sensors : Sensor_0335[2];
            action smooth : Common::Process;
            action forward : Common::Process;
            succession first smooth then forward;
            exhibit state lifecycle : Common::Lifecycle;
        }
        requirement controllerMass_0335 : Common::MassLimit {
            subject component : Controller_0335;
            attribute :>> limit = 2.0 [kg];
        }
    }

    package Subsystem_0336 {
        part def Sensor_0336 :> Common::Component {
            attribute :>> mass = 0.21 [kg];
            attribute :>> cost = 46.0;
            attribute range : Real = 136.0;
            port data : Common::DataPort;
        }
        part def Controller_0336 :> Common::Component {
            attribute :>> mass = 1.00 [kg];
            attribute :>> cost = 236.0;
            port supply : Common::PowerPort;
            part sensors : Sensor_0336[2];
            action smooth : Common::Process;
            action forward : Common::Process;
            succession first smooth then forward;
            exhibit state lifecycle : Common::Lifecycle;
        }
        requirement controllerMass_0336 : Common::MassLimit {
            subject component : Controller_0336;
            attribute :>> limit = 2.0 [kg];
        }
    }

    package Subsystem_0337 {
        part def Sensor_0337 :> Common::Component {
            attribute :>> mass = 0.22 [kg];
            attribute :>> cost = 47.0;
            attribute range : Real = 137.0;
            port data : Common::DataPort;
        }
        part def Controller_0337 :> Common::Component {
            attribute :>> mass = 1.10 [kg];
            attribute :>> cost = 237.0;
            port supply : Common::PowerPort;
            part sensors : Sensor_0337[2];
            action smooth : Common::Process;
            action forward : Common::Process;
            succession first smooth then forward;
            exhibit state lifecycle : Common::Lifecycle;
        }
        requirement controllerMass_0337 : Common::MassLimit {
            subject component : Controller_0337;
            attribute :>> limit = 2.0 [kg];
        }
    }

    package Subsystem_0338 {
        part def Sensor_0338 :> Common::Component {
            attribute :>> mass = 0.23 [kg];
            attribute :>> cost = 48.0;
            attribute range : Real = 138.0;
            port data : Common::DataPort;
        }
        part def Controller_0338 :> Common::Component {
            attribute :>> mass = 1.20 [kg];
            attribute :>> cost = 238.0;
            port supply : Common::PowerPort;
            part sensors : Sensor_0338[2];
            action smooth : Common::Process;
            action forward : Common::Process;
            succession first smooth then forward;
            exhibit state lifecycle : Common::Lifecycle;
        }
        requirement controllerMass_0338 : Common::MassLimit {
            subject component : Controller_0338;
            attribute :>> limit = 2.0 [kg];
        }
    }

    package Subsystem_0339 {
        part def Sensor_0339 :> Common::Component {
            attribute :>> mass = 0.24 [kg];
            attribute :>> cost = 49.0;
            attribute range : Real = 139.0;
            port data : Common::DataPort;
        }
        part def Controller_0339 :> Common::Component {
            attribute :>> mass = 1.30 [kg];
            attribute :>> cost = 239.0;
            port supply : Common::PowerPort;
            part sensors : Sensor_0339[2];
            action smooth : Common::Process;
            action forward : Common::Process;
            succession first smooth then forward;
            exhibit state lifecycle : Common::Lifecycle;
        }
        requirement controllerMass_0339 : Common::MassLimit {
            subject component : Controller_0339;
            attribute :>> limit = 2.0 [kg];
        }
    }

    package Subsystem_0340 {
        part def Sensor_0340 :> Common::Component {
            attribute :>> mass = 0.20 [kg];
            attribute :>> cost = 30.0;
            attribute range : Real = 140.0;
            port data : Common::DataPort;
        }
        part def Controller_0340 :> Common::Component {
            attribute :>> mass = 1.40 [kg];
            attribute :>> cost = 240.0;
            port supply : Common::PowerPort;
            part sensors : Sensor_0340[2];
            action smooth : Common::Process;
            action forward : Common::Process;
            succession first smooth then forward;
            exhibit state lifecycle : Common::Lifecycle;
        }
        requirement controllerMass_0340 : Common::MassLimit {
            subject component : Controller_0340;
            attribute :>> limit = 2.0 [kg];
        }
    }

    package Subsystem_0341 {
        part def Sensor_0341 :> Common::Component {
            attribute :>> mass = 0.21 [kg];
            attribute :>> cost = 31.0;
            attribute range : Real = 141.0;
            port data : Common::DataPort;
        }
        part def Controller_0341 :> Common::Component {
            attribute :>> mass = 1.50 [kg];
            attribute :>> cost = 241.0;
            port supply : Common::PowerPort;
            part sensors : Sensor_0341[2];
            action smooth : Common::Process;
            action forward : Common::Process;
            succession first smooth then forward;
            exhibit state lifecycle : Common::Lifecycle;
        }
        requirement controllerMass_0341 : Common::MassLimit {
            subject component : Controller_0341;
            attribute :>> limit = 2.0 [kg];
        }
    }

    package Subsystem_0342 {
        part def Sensor_0342 :> Common::Component {
            attribute :>> mass = 0.22 [kg];
            attribute :>> cost = 32.0;
            attribute range : Real = 142.0;
            port data : Common::DataPort;
        }
        part def Controller_0342 :> Common::Component {
            attribute :>> mass = 1.60 [kg];
            attribute :>> cost = 242.0;
            port supply : Common::PowerPort;
            part sensors : Sensor_0342[2];
            action smooth : Common::Process;
            action forward : Common::Process;
            succession first smooth then forward;
            exhibit state lifecycle : Common::Lifecycle;
        }
        requirement controllerMass_0342 : Common::MassLimit {
            subject component : Controller_0342;
            attribute :>> limit = 2.0 [kg];
        }
    }

    package Subsystem_0343 {
        part def Sensor_0343 :> Common::Component {
            attribute :>> mass = 0.23 [kg];
            attribute :>> cost = 33.0;
            attribute range : Real = 143.0;
            port data : Common::DataPort;
        }
        part def Controller_0343 :> Common::Component {
            attribute :>> mass = 1.00 [kg];
            attribute :>> cost = 243.0;
            port supply : Common::PowerPort;
            part sensors : Sensor_0343[2];
            action smooth : Common::Process;
            action forward : Common::Process;
            succession first smooth then forward;
            exhibit state lifecycle : Common::Lifecycle;
        }
        requirement controllerMass_0343 : Common::MassLimit {
            subject component : Controller_0343;
            attribute :>> limit = 2.0 [kg];
        }
    }

    package Subsystem_0344 {
        part def Sensor_0344 :> Common::Component {
            attribute :>> mass = 0.24 [kg];
            attribute :>> cost = 34.0;
            attribute range : Real = 144.0;
            port data : Common::DataPort;
        }
        part def Controller_0344 :> Common::Component {
            attribute :>> mass = 1.10 [kg];
            attribute :>> cost = 244.0;
            port supply : Common::PowerPort;
            part sensors : Sensor_0344[2];
            action smooth : Common::Process;
            action forward : Common::Process;
            succession first smooth then forward;
            exhibit state lifecycle : Common::Lifecycle;
        }
        requirement controllerMass_0344 : Common::MassLimit {
            subject component : Controller_0344;
            attribute :>> limit = 2.0 [kg];
        }
    }

    package Subsystem_0345 {
        part def Sensor_0345 :> Common::Component {
            attribute :>> mass = 0.20 [kg];
            attribute :>> cost = 35.0;
            attribute range : Real = 145.0;
            port data : Common::DataPort;
        }
        part def Controller_0345 :> Common::Component {
            attribute :>> mass = 1.20 [kg];
            attribute :>> cost = 245.0;
            port supply : Common::PowerPort;
            part sensors : Sensor_0345[2];
            action smooth : Common::Process;
            action forward : Common::Process;
            succession first smooth then forward;
            exhibit state lifecycle : Common::Lifecycle;
        }
        requirement controllerMass_0345 : Common::MassLimit {
            subject component : Controller_0345;
            attribute :>> limit = 2.0 [kg];
        }
    }

    package Subsystem_0346 {
        part def Sensor_0346 :> Common::Component {
            attribute :>> mass = 0.21 [kg];
            attribute :>> cost = 36.0;
            attribute range : Real = 146.0;
            port data : Common::DataPort;
        }
        part def Controller_0346 :> Common::Component {
            attribute :>> mass = 1.30 [kg];
            attribute :>> cost = 246.0;
            port supply : Common::PowerPort;
            part sensors : Sensor_0346[2];
            action smooth : Common::Process;
            action forward : Common::Process;
            succession first smooth then forward;
            exhibit state lifecycle : Common::Lifecycle;
        }
        requirement controllerMass_0346 : Common::MassLimit {
            subject component : Controller_0346;
            attribute :>> limit = 2.0 [kg];
        }
    }

    package Subsystem_0347 {
        part def Sensor_0347 :> Common::Component {
            attribute :>> mass = 0.22 [kg];
            attribute :>> cost = 37.0;
            attribute range : Real = 147.0;
            port data : Common::DataPort;
        }
        part def Controller_0347 :> Common::Component {
            attribute :>> mass = 1.40 [kg];
            attribute :>> cost = 247.0;
            port supply : Common::PowerPort;
            part sensors : Sensor_0347[2];
            action smooth : Common::Process;
            action forward : Common::Process;
            succession first smooth then forward;
            exhibit state lifecycle : Common::Lifecycle;
        }
        requirement controllerMass_0347 : Common::MassLimit {
            subject component : Controller_0347;
            attribute :>> limit = 2.0 [kg];
        }
    }

    package Subsystem_0348 {
        part def Sensor_0348 :> Common::Component {
            attribute :>> mass = 0.23 [kg];
            attribute :>> cost = 38.0;
            attribute range : Real = 148.0;
            port data : Common::DataPort;
        }
        part def Controller_0348 :> Common::Component {
            attribute :>> mass = 1.50 [kg];
            attribute :>> cost = 248.0;
            port supply : Common::PowerPort;
            part sensors : Sensor_0348[2];
            action smooth : Common::Process;
            action forward : Common::Process;
            succession first smooth then forward;
            exhibit state lifecycle : Common::Lifecycle;
        }
        requirement controllerMass_0348 : Common::MassLimit {
            subject component : Controller_0348;
            attribute :>> limit = 2.0 [kg];
        }
    }

    package Subsystem_0349 {
        part def Sensor_0349 :> Common::Component {
            attribute :>> mass = 0.24 [kg];
            attribute :>> cost = 39.0;
            attribute range : Real = 149.0;
            port data : Common::DataPort;
        }
        part def Controller_0349 :> Common::Component {
            attribute :>> mass = 1.60 [kg];
            attribute :>> cost = 249.0;
            port supply : Common::PowerPort;
            part sensors : Sensor_0349[2];
            action smooth : Common::Process;
            action forward : Common::Process;
            succession first smooth then forward;
            exhibit state lifecycle : Common::Lifecycle;
        }
        requirement controllerMass_0349 : Common::MassLimit {
            subject component : Controller_0349;
            attribute :>> limit = 2.0 [kg];
        }
    }

    package Subsystem_0350 {
        part def Sensor_0350 :> Common::Component {
            attribute :>> mass = 0.20 [kg];
            attribute :>> cost = 40.0;
            attribute range : Real = 100.0;
            port data : Common::DataPort;
        }
        part def Controller_0350 :> Common::Component {
            attribute :>> mass = 1.00 [kg];
            attribute :>> cost = 250.0;
            port supply : Common::PowerPort;
            part sensors : Sensor_0350[2];
            action smooth : Common::Process;
            action forward : Common::Process;
            succession first smooth then forward;
            exhibit state lifecycle : Common::Lifecycle;
        }
        requirement controllerMass_0350 : Common::MassLimit {
            subject component : Controller_0350;
            attribute :>> limit = 2.0 [kg];
        }
    }

    package Subsystem_0351 {
        part def Sensor_0351 :> Common::Component {
            attribute :>> mass = 0.21 [kg];
            attribute :>> cost = 41.0;
            attribute range : Real = 101.0;
            port data : Common::DataPort;
        }
        part def Controller_0351 :> Common::Component {
            attribute :>> mass = 1.10 [kg];
            attribute :>> cost = 251.0;
            port supply : Common::PowerPort;
            part sensors : Sensor_0351[2];
            action smooth : Common::Process;
            action forward : Common::Process;
            succession first smooth then forward;
            exhibit state lifecycle : Common::Lifecycle;
        }
        requirement controllerMass_0351 : Common::MassLimit {
            subject component : Controller_0351;
            attribute :>> limit = 2.0 [kg];
        }
    }

    package Subsystem_0352 {
        part def Sensor_0352 :> Common::Component {
            attribute :>> mass = 0.22 [kg];
            attribute :>> cost = 42.0;
            attribute range : Real = 102.0;
            port data : Common::DataPort;
        }
        part def Controller_0352 :> Common::Component {
            attribute :>> mass = 1.20 [kg];
            attribute :>> cost = 252.0;
            port supply : Common::PowerPort;
            part sensors : Sensor_0352[2];
            action smooth : Common::Process;
            action forward : Common::Process;
            succession first smooth then forward;
            exhibit state lifecycle : Common::Lifecycle;
        }
        requirement controllerMass_0352 : Common::MassLimit {
            subject component : Controller_0352;
            attribute :>> limit = 2.0 [kg];
        }
    }

    package Subsystem_0353 {
        part def Sensor_0353 :> Common::Component {
            attribute :>> mass = 0.23 [kg];
            attribute :>> cost = 43.0;
            attribute range : Real = 103.0;
            port data : Common::DataPort;
        }
        part def Controller_0353 :> Common::Component {
            attribute :>> mass = 1.30 [kg];
            attribute :>> cost = 253.0;
            port supply : Common::PowerPort;
            part sensors : Sensor_0353[2];
            action smooth : Common::Process;
            action forward : Common::Process;
            succession first smooth then forward;
            exhibit state lifecycle : Common::Lifecycle;
        }
        requirement controllerMass_0353 : Common::MassLimit {
            subject component : Controller_0353;
            attribute :>> limit = 2.0 [kg];
        }
    }

    package Subsystem_0354 {
        part def Sensor_0354 :> Common::Component {
            attribute :>> mass = 0.24 [kg];
            attribute :>> cost = 44.0;
            attribute range : Real = 104.0;
            port data : Common::DataPort;
        }
        part def Controller_0354 :> Common::Component {
            attribute :>> mass = 1.40 [kg];
            attribute :>> cost = 254.0;
            port supply : Common::PowerPort;
            part sensors : Sensor_0354[2];
            action smooth : Common::Process;
            action forward : Common::Process;
            succession first smooth then forward;
            exhibit state lifecycle : Common::Lifecycle;
        }
        requirement controllerMass_0354 : Common::MassLimit {
            subject component : Controller_0354;
            attribute :>> limit = 2.0 [kg];
        }
    }

    package Subsystem_0355 {
        part def Sensor_0355 :> Common::Component {
            attribute :>> mass = 0.20 [kg];
            attribute :>> cost = 45.0;
            attribute range : Real = 105.0;
            port data : Common::DataPort;
        }
        part def Controller_0355 :> Common::Component {
            attribute :>> mass = 1.50 [kg];
            attribute :>> cost = 255.0;
            port supply : Common::PowerPort;
            part sensors : Sensor_0355[2];
            action smooth : Common::Process;
            action forward : Common::Process;
            succession first smooth then forward;
            exhibit state lifecycle : Common::Lifecycle;
        }
        requirement controllerMass_0355 : Common::MassLimit {
            subject component : Controller_0355;
            attribute :>> limit = 2.0 [kg];
        }
    }

    package Subsystem_0356 {
        part def Sensor_0356 :> Common::Component {
            attribute :>> mass = 0.21 [kg];
            attribute :>> cost = 46.0;
            attribute range : Real = 106.0;
            port data : Common::DataPort;
        }
        part def Controller_0356 :> Common::Component {
            attribute :>> mass = 1.60 [kg];
            attribute :>> cost = 256.0;
            port supply : Common::PowerPort;
            part sensors : Sensor_0356[2];
            action smooth : Common::Process;
            action forward : Common::Process;
            succession first smooth then forward;
            exhibit state lifecycle : Common::Lifecycle;
        }
        requirement controllerMass_0356 : Common::MassLimit {
            subject component : Controller_0356;
            attribute :>> limit = 2.0 [kg];
        }
    }

    package Subsystem_0357 {
        part def Sensor_0357 :> Common::Component {
            attribute :>> mass = 0.22 [kg];
            attribute :>> cost = 47.0;
            attribute range : Real = 107.0;
            port data : Common::DataPort;
        }
        part def Controller_0357 :> Common::Component {
            attribute :>> mass = 1.00 [kg];
            attribute :>> cost = 257.0;
            port supply : Common::PowerPort;
            part sensors : Sensor_0357[2];
            action smooth : Common::Process;
            action forward : Common::Process;
            succession first smooth then forward;
            exhibit state lifecycle : Common::Lifecycle;
        }
        requirement controllerMass_0357 : Common::MassLimit {
            subject component : Controller_0357;
            attribute :>> limit = 2.0 [kg];
        }
    }

    package Subsystem_0358 {
        part def Sensor_0358 :> Common::Component {
            attribute :>> mass = 0.23 [kg];
            attribute :>> cost = 48.0;
            attribute range : Real = 108.0;
            port data : Common::DataPort;
        }
        part def Controller_0358 :> Common::Component {
            attribute :>> mass = 1.10 [kg];
            attribute :>> cost = 258.0;
            port supply : Common::PowerPort;
            part sensors : Sensor_0358[2];
            action smooth : Common::Process;
            action forward : Common::Process;
            succession first smooth then forward;
            exhibit state lifecycle : Common::Lifecycle;
        }
        requirement controllerMass_0358 : Common::MassLimit {
            subject component : Controller_0358;
            attribute :>> limit = 2.0 [kg];
        }
    }

    package Subsystem_0359 {
        part def Sensor_0359 :> Common::Component {
            attribute :>> mass = 0.24 [kg];
            attribute :>> cost = 49.0;
            attribute range : Real = 109.0;
            port data : Common::DataPort;
        }
        part def Controller_0359 :> Common::Component {
            attribute :>> mass = 1.20 [kg];
            attribute :>> cost = 259.0;
            port supply : Common::PowerPort;
            part sensors : Sensor_0359[2];
            action smooth : Common::Process;
            action forward : Common::Process;
            succession first smooth then forward;
            exhibit state lifecycle : Common::Lifecycle;
        }
        requirement controllerMass_0359 : Common::MassLimit {
            subject component : Controller_0359;
            attribute :>> limit = 2.0 [kg];
        }
    }

    package Subsystem_0360 {
        part def Sensor_0360 :> Common::Component {
            attribute :>> mass = 0.20 [kg];
            attribute :>> cost = 30.0;
            attribute range : Real = 110.0;
            port data : Common::DataPort;
        }
        part def Controller_0360 :> Common::Component {
            attribute :>> mass = 1.30 [kg];
            attribute :>> cost = 260.0;
            port supply : Common::PowerPort;
            part sensors : Sensor_0360[2];
            action smooth : Common::Process;
            action forward : Common::Process;
            succession first smooth then forward;
            exhibit state lifecycle : Common::Lifecycle;
        }
        requirement controllerMass_0360 : Common::MassLimit {
            subject component : Controller_0360;
            attribute :>> limit = 2.0 [kg];
        }
    }

    package Subsystem_0361 {
        part def Sensor_0361 :> Common::Component {
            attribute :>> mass = 0.21 [kg];
            attribute :>> cost = 31.0;
            attribute range : Real = 111.0;
            port data : Common::DataPort;
        }
        part def Controller_0361 :> Common::Component {
            attribute :>> mass = 1.40 [kg];
            attribute :>> cost = 261.0;
            port supply : Common::PowerPort;
            part sensors : Sensor_0361[2];
            action smooth : Common::Process;
            action forward : Common::Process;
            succession first smooth then forward;
            exhibit state lifecycle : Common::Lifecycle;
        }
        requirement controllerMass_0361 : Common::MassLimit {
            subject component : Controller_0361;
            attribute :>> limit = 2.0 [kg];
        }
    }

    package Subsystem_0362 {
        part def Sensor_0362 :> Common::Component {
            attribute :>> mass = 0.22 [kg];
            attribute :>> cost = 32.0;
            attribute range : Real = 112.0;
            port data : Common::DataPort;
        }
        part def Controller_0362 :> Common::Component {
            attribute :>> mass = 1.50 [kg];
            attribute :>> cost = 262.0;
            port supply : Common::PowerPort;
            part sensors : Sensor_0362[2];
            action smooth : Common::Process;
            action forward : Common::Process;
            succession first smooth then forward;
            exhibit state lifecycle : Common::Lifecycle;
        }
        requirement controllerMass_0362 : Common::MassLimit {
            subject component : Controller_0362;
            attribute :>> limit = 2.0 [kg];
        }
    }

    package Subsystem_0363 {
        part def Sensor_0363 :> Common::Component {
            attribute :>> mass = 0.23 [kg];
            attribute :>> cost = 33.0;
            attribute range : Real = 113.0;
            port data : Common::DataPort;
        }
        part def Controller_0363 :> Common::Component {
            attribute :>> mass = 1.60 [kg];
            attribute :>> cost = 263.0;
            port supply : Common::PowerPort;
            part sensors : Sensor_0363[2];
            action smooth : Common::Process;
            action forward : Common::Process;
            succession first smooth then forward;
            exhibit state lifecycle : Common::Lifecycle;
        }
        requirement controllerMass_0363 : Common::MassLimit {
            subject component : Controller_0363;
            attribute :>> limit = 2.0 [kg];
        }
    }

    package Subsystem_0364 {
        part def Sensor_0364 :> Common::Component {
            attribute :>> mass = 0.24 [kg];
            attribute :>> cost = 34.0;
            attribute range : Real = 114.0;
            port data : Common::DataPort;
        }
        part def Controller_0364 :> Common::Component {
            attribute :>> mass = 1.00 [kg];
            attribute :>> cost = 264.0;
            port supply : Common::PowerPort;
            part sensors : Sensor_0364[2];
            action smooth : Common::Process;
            action forward : Common::Process;
            succession first smooth then forward;
            exhibit state lifecycle : Common::Lifecycle;
        }
        requirement controllerMass_0364 : Common::MassLimit {
            subject component : Controller_0364;
            attribute :>> limit = 2.0 [kg];
        }
    }

    package Subsystem_0365 {
        part def Sensor_0365 :> Common::Component {
            attribute :>> mass = 0.20 [kg];
            attribute :>> cost = 35.0;
            attribute range : Real = 115.0;
            port data : Common::DataPort;
        }
        part def Controller_0365 :> Common::Component {
            attribute :>> mass = 1.10 [kg];
            attribute :>> cost = 265.0;
            port supply : Common::PowerPort;
            part sensors : Sensor_0365[2];
            action smooth : Common::Process;
            action forward : Common::Process;
            succession first smooth then forward;
            exhibit state lifecycle : Common::Lifecycle;
        }
        requirement controllerMass_0365 : Common::MassLimit {
            subject component : Controller_0365;
            attribute :>> limit = 2.0 [kg];
        }
    }

    package Subsystem_0366 {
        part def Sensor_0366 :> Common::Component {
            attribute :>> mass = 0.21 [kg];
            attribute :>> cost = 36.0;
            attribute range : Real = 116.0;
            port data : Common::DataPort;
        }
        part def Controller_0366 :> Common::Component {
            attribute :>> mass = 1.20 [kg];
            attribute :>> cost = 266.0;
            port supply : Common::PowerPort;
            part sensors : Sensor_0366[2];
            action smooth : Common::Process;
            action forward : Common::Process;
            succession first smooth then forward;
            exhibit state lifecycle : Common::Lifecycle;
        }
        requirement controllerMass_0366 : Common::MassLimit {
            subject component : Controller_0366;
            attribute :>> limit = 2.0 [kg];
        }
    }

    package Subsystem_0367 {
        part def Sensor_0367 :> Common::Component {
            attribute :>> mass = 0.22 [kg];
            attribute :>> cost = 37.0;
            attribute range : Real = 117.0;
            port data : Common::DataPort;
        }
        part def Controller_0367 :> Common::Component {
            attribute :>> mass = 1.30 [kg];
            attribute :>> cost = 267.0;
            port supply : Common::PowerPort;
            part sensors : Sensor_0367[2];
            action smooth : Common::Process;
            action forward : Common::Process;
            succession first smooth then forward;
            exhibit state lifecycle : Common::Lifecycle;
        }
        requirement controllerMass_0367 : Common::MassLimit {
            subject component : Controller_0367;
            attribute :>> limit = 2.0 [kg];
        }
    }

    package Subsystem_0368 {
        part def Sensor_0368 :> Common::Component {
            attribute :>> mass = 0.23 [kg];
            attribute :>> cost = 38.0;
            attribute range : Real = 118.0;
            port data : Common::DataPort;
        }
        part def Controller_0368 :> Common::Component {
            attribute :>> mass = 1.40 [kg];
            attribute :>> cost = 268.0;
            port supply : Common::PowerPort;
            part sensors : Sensor_0368[2];
            action smooth : Common::Process;
            action forward : Common::Process;
            succession first smooth then forward;
            exhibit state lifecycle : Common::Lifecycle;
        }
        requirement controllerMass_0368 : Common::MassLimit {
            subject component : Controller_0368;
            attribute :>> limit = 2.0 [kg];
        }
    }

    package Subsystem_0369 {
        part def Sensor_0369 :> Common::Component {
            attribute :>> mass = 0.24 [kg];
            attribute :>> cost = 39.0;
            attribute range : Real = 119.0;
            port data : Common::DataPort;
        }
        part def Controller_0369 :> Common::Component {
            attribute :>> mass = 1.50 [kg];
            attribute :>> cost = 269.0;
            port supply : Common::PowerPort;
            part sensors : Sensor_0369[2];
            action smooth : Common::Process;
            action forward : Common::Process;
            succession first smooth then forward;
            exhibit state lifecycle : Common::Lifecycle;
        }
        requirement controllerMass_0369 : Common::MassLimit {
            subject component : Controller_0369;
            attribute :>> limit = 2.0 [kg];
        }
    }

    package Subsystem_0370 {
        part def Sensor_0370 :> Common::Component {
            attribute :>> mass = 0.20 [kg];
            attribute :>> cost = 40.0;
            attribute range : Real = 120.0;
            port data : Common::DataPort;
        }
        part def Controller_0370 :> Common::Component {
            attribute :>> mass = 1.60 [kg];
            attribute :>> cost = 270.0;
            port supply : Common::PowerPort;
            part sensors : Sensor_0370[2];
            action smooth : Common::Process;
            action forward : Common::Process;
            succession first smooth then forward;
            exhibit state lifecycle : Common::Lifecycle;
        }
        requirement controllerMass_0370 : Common::MassLimit {
            subject component : Controller_0370;
            attribute :>> limit = 2.0 [kg];
        }
    }

    package Subsystem_0371 {
        part def Sensor_0371 :> Common::Component {
            attribute :>> mass = 0.21 [kg];
            attribute :>> cost = 41.0;
            attribute range : Real = 121.0;
            port data : Common::DataPort;
        }
        part def Controller_0371 :> Common::Component {
            attribute :>> mass = 1.00 [kg];
            attribute :>> cost = 271.0;
            port supply : Common::PowerPort;
            part sensors : Sensor_0371[2];
            action smooth : Common::Process;
            action forward : Common::Process;
            succession first smooth then forward;
            exhibit state lifecycle : Common::Lifecycle;
        }
        requirement controllerMass_0371 : Common::MassLimit {
            subject component : Controller_0371;
            attribute :>> limit = 2.0 [kg];
        }
    }

    package Subsystem_0372 {
        part def Sensor_0372 :> Common::Component {
            attribute :>> mass = 0.22 [kg];
            attribute :>> cost = 42.0;
            attribute range : Real = 122.0;
            port data : Common::DataPort;
        }
        part def Controller_0372 :> Common::Component {
            attribute :>> mass = 1.10 [kg];
            attribute :>> cost = 272.0;
            port supply : Common::PowerPort;
            part sensors : Sensor_0372[2];
            action smooth : Common::Process;
            action forward : Common::Process;
            succession first smooth then forward;
            exhibit state lifecycle : Common::Lifecycle;
        }
        requirement controllerMass_0372 : Common::MassLimit {
            subject component : Controller_0372;
            attribute :>> limit = 2.0 [kg];
        }
    }

    package Subsystem_0373 {
        part def Sensor_0373 :> Common::Component {
            attribute :>> mass = 0.23 [kg];
            attribute :>> cost = 43.0;
            attribute range : Real = 123.0;
            port data : Common::DataPort;
        }
        part def Controller_0373 :> Common::Component {
            attribute :>> mass = 1.20 [kg];
            attribute :>> cost = 273.0;
            port supply : Common::PowerPort;
            part sensors : Sensor_0373[2];
            action smooth : Common::Process;
            action forward : Common::Process;
            succession first smooth then forward;
            exhibit state lifecycle : Common::Lifecycle;
        }
        requirement controllerMass_0373 : Common::MassLimit {
            subject component : Controller_0373;
            attribute :>> limit = 2.0 [kg];
        }
    }

    package Subsystem_0374 {
        part def Sensor_0374 :> Common::Component {
            attribute :>> mass = 0.24 [kg];
            attribute :>> cost = 44.0;
            attribute range : Real = 124.0;
            port data : Common::DataPort;
        }
        part def Controller_0374 :> Common::Component {
            attribute :>> mass = 1.30 [kg];
            attribute :>> cost = 274.0;
            port supply : Common::PowerPort;
            part sensors : Sensor_0374[2];
            action smooth : Common::Process;
            action forward : Common::Process;
            succession first smooth then forward;
            exhibit state lifecycle : Common::Lifecycle;
        }
        requirement controllerMass_0374 : Common::MassLimit {
            subject component : Controller_0374;
            attribute :>> limit = 2.0 [kg];
        }
    }

    package Subsystem_0375 {
        part def Sensor_0375 :> Common::Component {
            attribute :>> mass = 0.20 [kg];
            attribute :>> cost = 45.0;
            attribute range : Real = 125.0;
            port data : Common::DataPort;
        }
        part def Controller_0375 :> Common::Component {
            attribute :>> mass = 1.40 [kg];
            attribute :>> cost = 275.0;
            port supply : Common::PowerPort;
            part sensors : Sensor_0375[2];
            action smooth : Common::Process;
            action forward : Common::Process;
            succession first smooth then forward;
            exhibit state lifecycle : Common::Lifecycle;
        }
        requirement controllerMass_0375 : Common::MassLimit {
            subject component : Controller_0375;
            attribute :>> limit = 2.0 [kg];
        }
    }

    package Subsystem_0376 {
        part def Sensor_0376 :> Common::Component {
            attribute :>> mass = 0.21 [kg];
            attribute :>> cost = 46.0;
            attribute range : Real = 126.0;
            port data : Common::DataPort;
        }
        part def Controller_0376 :> Common::Component {
            attribute :>> mass = 1.50 [kg];
            attribute :>> cost = 276.0;
            port supply : Common::PowerPort;
            part sensors : Sensor_0376[2];
            action smooth : Common::Process;
            action forward : Common::Process;
            succession first smooth then forward;
            exhibit state lifecycle : Common::Lifecycle;
        }
        requirement controllerMass_0376 : Common::MassLimit {
            subject component : Controller_0376;
            attribute :>> limit = 2.0 [kg];
        }
    }

    package Subsystem_0377 {
        part def Sensor_0377 :> Common::Component {
            attribute :>> mass = 0.22 [kg];
            attribute :>> cost = 47.0;
            attribute range : Real = 127.0;
            port data : Common::DataPort;
        }
        part def Controller_0377 :> Common::Component {
            attribute :>> mass = 1.60 [kg];
            attribute :>> cost = 277.0;
            port supply : Common::PowerPort;
            part sensors : Sensor_0377[2];
            action smooth : Common::Process;
            action forward : Common::Process;
            succession first smooth then forward;
            exhibit state lifecycle : Common::Lifecycle;
        }
        requirement controllerMass_0377 : Common::MassLimit {
            subject component : Controller_0377;
            attribute :>> limit = 2.0 [kg];
        }
    }

    package Subsystem_0378 {
        part def Sensor_0378 :> Common::Component {
            attribute :>> mass = 0.23 [kg];
            attribute :>> cost = 48.0;
            attribute range : Real = 128.0;
            port data : Common::DataPort;
        }
        part def Controller_0378 :> Common::Component {
            attribute :>> mass = 1.00 [kg];
            attribute :>> cost = 278.0;
            port supply : Common::PowerPort;
            part sensors : Sensor_0378[2];
            action smooth : Common::Process;
            action forward : Common::Process;
            succession first smooth then forward;
            exhibit state lifecycle : Common::Lifecycle;
        }
        requirement controllerMass_0378 : Common::MassLimit {
            subject component : Controller_0378;
            attribute :>> limit = 2.0 [kg];
        }
    }

    package Subsystem_0379 {
        part def Sensor_0379 :> Common::Component {
            attribute :>> mass = 0.24 [kg];
            attribute :>> cost = 49.0;
            attribute range : Real = 129.0;
            port data : Common::DataPort;
        }
        part def Controller_0379 :> Common::Component {
            attribute :>> mass = 1.10 [kg];
            attribute :>> cost = 279.0;
            port supply : Common::PowerPort;
            part sensors : Sensor_0379[2];
            action smooth : Common::Process;
            action forward : Common::Process;
            succession first smooth then forward;
            exhibit state lifecycle : Common::Lifecycle;
        }
        requirement controllerMass_0379 : Common::MassLimit {
            subject component : Controller_0379;
            attribute :>> limit = 2.0 [kg];
        }
    }

    package Subsystem_0380 {
        part def Sensor_0380 :> Common::Component {
            attribute :>> mass = 0.20 [kg];
            attribute :>> cost = 30.0;
            attribute range : Real = 130.0;
            port data : Common::DataPort;
        }
        part def Controller_0380 :> Common::Component {
            attribute :>> mass = 1.20 [kg];
            attribute :>> cost = 280.0;
            port supply : Common::PowerPort;
            part sensors : Sensor_0380[2];
            action smooth : Common::Process;
            action forward : Common::Process;
            succession first smooth then forward;
            exhibit state lifecycle : Common::Lifecycle;
        }
        requirement controllerMass_0380 : Common::MassLimit {
            subject component : Controller_0380;
            attribute :>> limit = 2.0 [kg];
        }
    }

    package Subsystem_0381 {
        part def Sensor_0381 :> Common::Component {
            attribute :>> mass = 0.21 [kg];
            attribute :>> cost = 31.0;
            attribute range : Real = 131.0;
            port data : Common::DataPort;
        }
        part def Controller_0381 :> Common::Component {
            attribute :>> mass = 1.30 [kg];
            attribute :>> cost = 281.0;
            port supply : Common::PowerPort;
            part sensors : Sensor_0381[2];
            action smooth : Common::Process;
            action forward : Common::Process;
            succession first smooth then forward;
            exhibit state lifecycle : Common::Lifecycle;
        }
        requirement controllerMass_0381 : Common::MassLimit {
            subject component : Controller_0381;
            attribute :>> limit = 2.0 [kg];
        }
    }

    package Subsystem_0382 {
        part def Sensor_0382 :> Common::Component {
            attribute :>> mass = 0.22 [kg];
            attribute :>> cost = 32.0;
            attribute range : Real = 132.0;
            port data : Common::DataPort;
        }
        part def Controller_0382 :> Common::Component {
            attribute :>> mass = 1.40 [kg];
            attribute :>> cost = 282.0;
            port supply : Common::PowerPort;
            part sensors : Sensor_0382[2];
            action smooth : Common::Process;
            action forward : Common::Process;
            succession first smooth then forward;
            exhibit state lifecycle : Common::Lifecycle;
        }
        requirement controllerMass_0382 : Common::MassLimit {
            subject component : Controller_0382;
            attribute :>> limit = 2.0 [kg];
        }
    }

    package Subsystem_0383 {
        part def Sensor_0383 :> Common::Component {
            attribute :>> mass = 0.23 [kg];
            attribute :>> cost = 33.0;
            attribute range : Real = 133.0;
            port data : Common::DataPort;
        }
        part def Controller_0383 :> Common::Component {
            attribute :>> mass = 1.50 [kg];
            attribute :>> cost = 283.0;
            port supply : Common::PowerPort;
            part sensors : Sensor_0383[2];
            action smooth : Common::Process;
            action forward : Common::Process;
            succession first smooth then forward;
            exhibit state lifecycle : Common::Lifecycle;
        }
        requirement controllerMass_0383 : Common::MassLimit {
            subject component : Controller_0383;
            attribute :>> limit = 2.0 [kg];
        }
    }

    package Subsystem_0384 {
        part def Sensor_0384 :> Common::Component {
            attribute :>> mass = 0.24 [kg];
            attribute :>> cost = 34.0;
            attribute range : Real = 134.0;
            port data : Common::DataPort;
        }
        part def Controller_0384 :> Common::Component {
            attribute :>> mass = 1.60 [kg];
            attribute :>> cost = 284.0;
            port supply : Common::PowerPort;
            part sensors : Sensor_0384[2];
            action smooth : Common::Process;
            action forward : Common::Process;
            succession first smooth then forward;
            exhibit state lifecycle : Common::Lifecycle;
        }
        requirement controllerMass_0384 : Common::MassLimit {
            subject component : Controller_0384;
            attribute :>> limit = 2.0 [kg];
        }
    }

    package Subsystem_0385 {
        part def Sensor_0385 :> Common::Component {
            attribute :>> mass = 0.20 [kg];
            attribute :>> cost = 35.0;
            attribute range : Real = 135.0;
            port data : Common::DataPort;
        }
        part def Controller_0385 :> Common::Component {
            attribute :>> mass = 1.00 [kg];
            attribute :>> cost = 285.0;
            port supply : Common::PowerPort;
            part sensors : Sensor_0385[2];
            action smooth : Common::Process;
            action forward : Common::Process;
            succession first smooth then forward;
            exhibit state lifecycle : Common::Lifecycle;
        }
        requirement controllerMass_0385 : Common::MassLimit {
            subject component : Controller_0385;
            attribute :>> limit = 2.0 [kg];
        }
    }

    package Subsystem_0386 {
        part def Sensor_0386 :> Common::Component {
            attribute :>> mass = 0.21 [kg];
            attribute :>> cost = 36.0;
            attribute range : Real = 136.0;
            port data : Common::DataPort;
        }
        part def Controller_0386 :> Common::Component {
            attribute :>> mass = 1.10 [kg];
            attribute :>> cost = 286.0;
            port supply : Common::PowerPort;
            part sensors : Sensor_0386[2];
            action smooth : Common::Process;
            action forward : Common::Process;
            succession first smooth then forward;
            exhibit state lifecycle : Common::Lifecycle;
        }
        requirement controllerMass_0386 : Common::MassLimit {
            subject component : Controller_0386;
            attribute :>> limit = 2.0 [kg];
        }
    }

    package Subsystem_0387 {
        part def Sensor_0387 :> Common::Component {
            attribute :>> mass = 0.22 [kg];
            attribute :>> cost = 37.0;
            attribute range : Real = 137.0;
            port data : Common::DataPort;
        }
        part def Controller_0387 :> Common::Component {
            attribute :>> mass = 1.20 [kg];
            attribute :>> cost = 287.0;
            port supply : Common::PowerPort;
            part sensors : Sensor_0387[2];
            action smooth : Common::Process;
            action forward : Common::Process;
            succession first smooth then forward;
            exhibit state lifecycle : Common::Lifecycle;
        }
        requirement controllerMass_0387 : Common::MassLimit {
            subject component : Controller_0387;
            attribute :>> limit = 2.0 [kg];
        }
    }

    package Subsystem_0388 {
        part def Sensor_0388 :> Common::Component {
            attribute :>> mass = 0.23 [kg];
            attribute :>> cost = 38.0;
            attribute range : Real = 138.0;
            port data : Common::DataPort;
        }
        part def Controller_0388 :> Common::Component {
            attribute :>> mass = 1.30 [kg];
            attribute :>> cost = 288.0;
            port supply : Common::PowerPort;
            part sensors : Sensor_0388[2];
            action smooth : Common::Process;
            action forward : Common::Process;
            succession first smooth then forward;
            exhibit state lifecycle : Common::Lifecycle;
        }
        requirement controllerMass_0388 : Common::MassLimit {
            subject component : Controller_0388;
            attribute :>> limit = 2.0 [kg];
        }
    }

    package Subsystem_0389 {
        part def Sensor_0389 :> Common::Component {
            attribute :>> mass = 0.24 [kg];
            attribute :>> cost = 39.0;
            attribute range : Real = 139.0;
            port data : Common::DataPort;
        }
        part def Controller_0389 :> Common::Component {
            attribute :>> mass = 1.40 [kg];
            attribute :>> cost = 289.0;
            port supply : Common::PowerPort;
            part sensors : Sensor_0389[2];
            action smooth : Common::Process;
            action forward : Common::Process;
            succession first smooth then forward;
            exhibit state lifecycle : Common::Lifecycle;
        }
        requirement controllerMass_0389 : Common::MassLimit {
            subject component : Controller_0389;
            attribute :>> limit = 2.0 [kg];
        }
    }

    package Subsystem_0390 {
        part def Sensor_0390 :> Common::Component {
            attribute :>> mass = 0.20 [kg];
            attribute :>> cost = 40.0;
            attribute range : Real = 140.0;
            port data : Common::DataPort;
        }
        part def Controller_0390 :> Common::Component {
            attribute :>> mass = 1.50 [kg];
            attribute :>> cost = 290.0;
            port supply : Common::PowerPort;
            part sensors : Sensor_0390[2];
            action smooth : Common::Process;
            action forward : Common::Process;
            succession first smooth then forward;
            exhibit state lifecycle : Common::Lifecycle;
        }
        requirement controllerMass_0390 : Common::MassLimit {
            subject component : Controller_0390;
            attribute :>> limit = 2.0 [kg];
        }
    }

    package Subsystem_0391 {
        part def Sensor_0391 :> Common::Component {
            attribute :>> mass = 0.21 [kg];
            attribute :>> cost = 41.0;
            attribute range : Real = 141.0;
            port data : Common::DataPort;
        }
        part def Controller_0391 :> Common::Component {
            attribute :>> mass = 1.60 [kg];
            attribute :>> cost = 291.0;
            port supply : Common::PowerPort;
            part sensors : Sensor_0391[2];
            action smooth : Common::Process;
            action forward : Common::Process;
            succession first smooth then forward;
            exhibit state lifecycle : Common::Lifecycle;
        }
        requirement controllerMass_0391 : Common::MassLimit {
            subject component : Controller_0391;
            attribute :>> limit = 2.0 [kg];
        }
    }

    package Subsystem_0392 {
        part def Sensor_0392 :> Common::Component {
            attribute :>> mass = 0.22 [kg];
            attribute :>> cost = 42.0;
            attribute range : Real = 142.0;
            port data : Common::DataPort;
        }
        part def Controller_0392 :> Common::Component {
            attribute :>> mass = 1.00 [kg];
            attribute :>> cost = 292.0;
            port supply : Common::PowerPort;
            part sensors : Sensor_0392[2];
            action smooth : Common::Process;
            action forward : Common::Process;
            succession first smooth then forward;
            exhibit state lifecycle : Common::Lifecycle;
        }
        requirement controllerMass_0392 : Common::MassLimit {
            subject component : Controller_0392;
            attribute :>> limit = 2.0 [kg];
        }
    }

    package Subsystem_0393 {
        part def Sensor_0393 :> Common::Component {
            attribute :>> mass = 0.23 [kg];
            attribute :>> cost = 43.0;
            attribute range : Real = 143.0;
            port data : Common::DataPort;
        }
        part def Controller_0393 :> Common::Component {
            attribute :>> mass = 1.10 [kg];
            attribute :>> cost = 293.0;
            port supply : Common::PowerPort;
            part sensors : Sensor_0393[2];
            action smooth : Common::Process;
            action forward : Common::Process;
            succession first smooth then forward;
            exhibit state lifecycle : Common::Lifecycle;
        }
        requirement controllerMass_0393 : Common::MassLimit {
            subject component : Controller_0393;
            attribute :>> limit = 2.0 [kg];
        }
    }

    package Subsystem_0394 {
        part def Sensor_0394 :> Common::Component {
            attribute :>> mass = 0.24 [kg];
            attribute :>> cost = 44.0;
            attribute range : Real = 144.0;
            port data : Common::DataPort;
        }
        part def Controller_0394 :> Common::Component {
            attribute :>> mass = 1.20 [kg];
            attribute :>> cost = 294.0;
            port supply : Common::PowerPort;
            part sensors : Sensor_0394[2];
            action smooth : Common::Process;
            action forward : Common::Process;
            succession first smooth then forward;
            exhibit state lifecycle : Common::Lifecycle;
        }
        requirement controllerMass_0394 : Common::MassLimit {
            subject component : Controller_0394;
            attribute :>> limit = 2.0 [kg];
        }
    }

    package Subsystem_0395 {
        part def Sensor_0395 :> Common::Component {
            attribute :>> mass = 0.20 [kg];
            attribute :>> cost = 45.0;
            attribute range : Real = 145.0;
            port data : Common::DataPort;
        }
        part def Controller_0395 :> Common::Component {
            attribute :>> mass = 1.30 [kg];
            attribute :>> cost = 295.0;
            port supply : Common::PowerPort;
            part sensors : Sensor_0395[2];
            action smooth : Common::Process;
            action forward : Common::Process;
            succession first smooth then forward;
            exhibit state lifecycle : Common::Lifecycle;
        }
        requirement controllerMass_0395 : Common::MassLimit {
            subject component : Controller_0395;
            attribute :>> limit = 2.0 [kg];
        }
    }

    package Subsystem_0396 {
        part def Sensor_0396 :> Common::Component {
            attribute :>> mass = 0.21 [kg];
            attribute :>> cost = 46.0;
            attribute range : Real = 146.0;
            port data : Common::DataPort;
        }
        part def Controller_0396 :> Common::Component {
            attribute :>> mass = 1.40 [kg];
            attribute :>> cost = 296.0;
            port supply : Common::PowerPort;
            part sensors : Sensor_0396[2];
            action smooth : Common::Process;
            action forward : Common::Process;
            succession first smooth then forward;
            exhibit state lifecycle : Common::Lifecycle;
        }
        requirement controllerMass_0396 : Common::MassLimit {
            subject component : Controller_0396;
            attribute :>> limit = 2.0 [kg];
        }
    }

    package Subsystem_0397 {
        part def Sensor_0397 :> Common::Component {
            attribute :>> mass = 0.22 [kg];
            attribute :>> cost = 47.0;
            attribute range : Real = 147.0;
            port data : Common::DataPort;
        }
        part def Controller_0397 :> Common::Component {
            attribute :>> mass = 1.50 [kg];
            attribute :>> cost = 297.0;
            port supply : Common::PowerPort;
            part sensors : Sensor_0397[2];
            action smooth : Common::Process;
            action forward : Common::Process;
            succession first smooth then forward;
            exhibit state lifecycle : Common::Lifecycle;
        }
        requirement controllerMass_0397 : Common::MassLimit {
            subject component : Controller_0397;
            attribute :>> limit = 2.0 [kg];
        }
    }

    package Subsystem_0398 {
        part def Sensor_0398 :> Common::Component {
            attribute :>> mass = 0.23 [kg];
            attribute :>> cost = 48.0;
            attribute range : Real = 148.0;
            port data : Common::DataPort;
        }
        part def Controller_0398 :> Common::Component {
            attribute :>> mass = 1.60 [kg];
            attribute :>> cost = 298.0;
            port supply : Common::PowerPort;
            part sensors : Sensor_0398[2];
            action smooth : Common::Process;
            action forward : Common::Process;
            succession first smooth then forward;
            exhibit state lifecycle : Common::Lifecycle;
        }
        requirement controllerMass_0398 : Common::MassLimit {
            subject component : Controller_0398;
            attribute :>> limit = 2.0 [kg];
        }
    }

    package Subsystem_0399 {
        part def Sensor_0399 :> Common::Component {
            attribute :>> mass = 0.24 [kg];
            attribute :>> cost = 49.0;
            attribute range : Real = 149.0;
            port data : Common::DataPort;
        }
        part def Controller_0399 :> Common::Component {
            attribute :>> mass = 1.00 [kg];
            attribute :>> cost = 299.0;
            port supply : Common::PowerPort;
            part sensors : Sensor_0399[2];
            action smooth : Common::Process;
            action forward : Common::Process;
            succession first smooth then forward;
            exhibit state lifecycle : Common::Lifecycle;
        }
        requirement controllerMass_0399 : Common::MassLimit {
            subject component : Controller_0399;
            attribute :>> limit = 2.0 [kg];
        }
    }

    package Subsystem_0400 {
        part def Sensor_0400 :> Common::Component {
            attribute :>> mass = 0.20 [kg];
            attribute :>> cost = 30.0;
            attribute range : Real = 100.0;
            port data : Common::DataPort;
        }
        part def Controller_0400 :> Common::Component {
            attribute :>> mass = 1.10 [kg];
            attribute :>> cost = 200.0;
            port supply : Common::PowerPort;
            part sensors : Sensor_0400[2];
            action smooth : Common::Process;
            action forward : Common::Process;
            succession first smooth then forward;
            exhibit state lifecycle : Common::Lifecycle;
        }
        requirement controllerMass_0400 : Common::MassLimit {
            subject component : Controller_0400;
            attribute :>> limit = 2.0 [kg];
        }
    }

    package Subsystem_0401 {
        part def Sensor_0401 :> Common::Component {
            attribute :>> mass = 0.21 [kg];
            attribute :>> cost = 31.0;
            attribute range : Real = 101.0;
            port data : Common::DataPort;
        }
        part def Controller_0401 :> Common::Component {
            attribute :>> mass = 1.20 [kg];
            attribute :>> cost = 201.0;
            port supply : Common::PowerPort;
            part sensors : Sensor_0401[2];
            action smooth : Common::Process;
            action forward : Common::Process;
            succession first smooth then forward;
            exhibit state lifecycle : Common::Lifecycle;
        }
        requirement controllerMass_0401 : Common::MassLimit {
            subject component : Controller_0401;
            attribute :>> limit = 2.0 [kg];
        }
    }

    package Subsystem_0402 {
        part def Sensor_0402 :> Common::Component {
            attribute :>> mass = 0.22 [kg];
            attribute :>> cost = 32.0;
            attribute range : Real = 102.0;
            port data : Common::DataPort;
        }
        part def Controller_0402 :> Common::Component {
            attribute :>> mass = 1.30 [kg];
            attribute :>> cost = 202.0;
            port supply : Common::PowerPort;
            part sensors : Sensor_0402[2];
            action smooth : Common::Process;
            action forward : Common::Process;
            succession first smooth then forward;
            exhibit state lifecycle : Common::Lifecycle;
        }
        requirement controllerMass_0402 : Common::MassLimit {
            subject component : Controller_0402;
            attribute :>> limit = 2.0 [kg];
        }
    }

    package Subsystem_0403 {
        part def Sensor_0403 :> Common::Component {
            attribute :>> mass = 0.23 [kg];
            attribute :>> cost = 33.0;
            attribute range : Real = 103.0;
            port data : Common::DataPort;
        }
        part def Controller_0403 :> Common::Component {
            attribute :>> mass = 1.40 [kg];
            attribute :>> cost = 203.0;
            port supply : Common::PowerPort;
            part sensors : Sensor_0403[2];
            action smooth : Common::Process;
            action forward : Common::Process;
            succession first smooth then forward;
            exhibit state lifecycle : Common::Lifecycle;
        }
        requirement controllerMass_0403 : Common::MassLimit {
            subject component : Controller_0403;
            attribute :>> limit = 2.0 [kg];
        }
    }

    package Subsystem_0404 {
        part def Sensor_0404 :> Common::Component {
            attribute :>> mass = 0.24 [kg];
            attribute :>> cost = 34.0;
            attribute range : Real = 104.0;
            port data : Common::DataPort;
        }
        part def Controller_0404 :> Common::Component {
            attribute :>> mass = 1.50 [kg];
            attribute :>> cost = 204.0;
            port supply : Common::PowerPort;
            part sensors : Sensor_0404[2];
            action smooth : Common::Process;
            action forward : Common::Process;
            succession first smooth then forward;
            exhibit state lifecycle : Common::Lifecycle;
        }
        requirement controllerMass_0404 : Common::MassLimit {
            subject component : Controller_0404;
            attribute :>> limit = 2.0 [kg];
        }
    }

    package Subsystem_0405 {
        part def Sensor_0405 :> Common::Component {
            attribute :>> mass = 0.20 [kg];
            attribute :>> cost = 35.0;
            attribute range : Real = 105.0;
            port data : Common::DataPort;
        }
        part def Controller_0405 :> Common::Component {
            attribute :>> mass = 1.60 [kg];
            attribute :>> cost = 205.0;
            port supply : Common::PowerPort;
            part sensors : Sensor_0405[2];
            action smooth : Common::Process;
            action forward : Common::Process;
            succession first smooth then forward;
            exhibit state lifecycle : Common::Lifecycle;
        }
        requirement controllerMass_0405 : Common::MassLimit {
            subject component : Controller_0405;
            attribute :>> limit = 2.0 [kg];
        }
    }

    package Subsystem_0406 {
        part def Sensor_0406 :> Common::Component {
            attribute :>> mass = 0.21 [kg];
            attribute :>> cost = 36.0;
            attribute range : Real = 106.0;
            port data : Common::DataPort;
        }
        part def Controller_0406 :> Common::Component {
            attribute :>> mass = 1.00 [kg];
            attribute :>> cost = 206.0;
            port supply : Common::PowerPort;
            part sensors : Sensor_0406[2];
            action smooth : Common::Process;
            action forward : Common::Process;
            succession first smooth then forward;
            exhibit state lifecycle : Common::Lifecycle;
        }
        requirement controllerMass_0406 : Common::MassLimit {
            subject component : Controller_0406;
            attribute :>> limit = 2.0 [kg];
        }
    }

    package Subsystem_0407 {
        part def Sensor_0407 :> Common::Component {
            attribute :>> mass = 0.22 [kg];
            attribute :>> cost = 37.0;
            attribute range : Real = 107.0;
            port data : Common::DataPort;
        }
        part def Controller_0407 :> Common::Component {
            attribute :>> mass = 1.10 [kg];
            attribute :>> cost = 207.0;
            port supply : Common::PowerPort;
            part sensors : Sensor_0407[2];
            action smooth : Common::Process;
            action forward : Common::Process;
            succession first smooth then forward;
            exhibit state lifecycle : Common::Lifecycle;
        }
        requirement controllerMass_0407 : Common::MassLimit {
            subject component : Controller_0407;
            attribute :>> limit = 2.0 [kg];
        }
    }

    package Subsystem_0408 {
        part def Sensor_0408 :> Common::Component {
            attribute :>> mass = 0.23 [kg];
            attribute :>> cost = 38.0;
            attribute range : Real = 108.0;
            port data : Common::DataPort;
        }
        part def Controller_0408 :> Common::Component {
            attribute :>> mass = 1.20 [kg];
            attribute :>> cost = 208.0;
            port supply : Common::PowerPort;
            part sensors : Sensor_0408[2];
            action smooth : Common::Process;
            action forward : Common::Process;
            succession first smooth then forward;
            exhibit state lifecycle : Common::Lifecycle;
        }
        requirement controllerMass_0408 : Common::MassLimit {
            subject component : Controller_0408;
            attribute :>> limit = 2.0 [kg];
        }
    }

    package Subsystem_0409 {
        part def Sensor_0409 :> Common::Component {
            attribute :>> mass = 0.24 [kg];
            attribute :>> cost = 39.0;
            attribute range : Real = 109.0;
            port data : Common::DataPort;
        }
        part def Controller_0409 :> Common::Component {
            attribute :>> mass = 1.30 [kg];
            attribute :>> cost = 209.0;
            port supply : Common::PowerPort;
            part sensors : Sensor_0409[2];
            action smooth : Common::Process;
            action forward : Common::Process;
            succession first smooth then forward;
            exhibit state lifecycle : Common::Lifecycle;
        }
        requirement controllerMass_0409 : Common::MassLimit {
            subject component : Controller_0409;
            attribute :>> limit = 2.0 [kg];
        }
    }

    package Subsystem_0410 {
        part def Sensor_0410 :> Common::Component {
            attribute :>> mass = 0.20 [kg];
            attribute :>> cost = 40.0;
            attribute range : Real = 110.0;
            port data : Common::DataPort;
        }
        part def Controller_0410 :> Common::Component {
            attribute :>> mass = 1.40 [kg];
            attribute :>> cost = 210.0;
            port supply : Common::PowerPort;
            part sensors : Sensor_0410[2];
            action smooth : Common::Process;
            action forward : Common::Process;
            succession first smooth then forward;
            exhibit state lifecycle : Common::Lifecycle;
        }
        requirement controllerMass_0410 : Common::MassLimit {
            subject component : Controller_0410;
            attribute :>> limit = 2.0 [kg];
        }
    }

    package Subsystem_0411 {
        part def Sensor_0411 :> Common::Component {
            attribute :>> mass = 0.21 [kg];
            attribute :>> cost = 41.0;
            attribute range : Real = 111.0;
            port data : Common::DataPort;
        }
        part def Controller_0411 :> Common::Component {
            attribute :>> mass = 1.50 [kg];
            attribute :>> cost = 211.0;
            port supply : Common::PowerPort;
            part sensors : Sensor_0411[2];
            action smooth : Common::Process;
            action forward : Common::Process;
            succession first smooth then forward;
            exhibit state lifecycle : Common::Lifecycle;
        }
        requirement controllerMass_0411 : Common::MassLimit {
            subject component : Controller_0411;
            attribute :>> limit = 2.0 [kg];
        }
    }

    package Subsystem_0412 {
        part def Sensor_0412 :> Common::Component {
            attribute :>> mass = 0.22 [kg];
            attribute :>> cost = 42.0;
            attribute range : Real = 112.0;
            port data : Common::DataPort;
        }
        part def Controller_0412 :> Common::Component {
            attribute :>> mass = 1.60 [kg];
            attribute :>> cost = 212.0;
            port supply : Common::PowerPort;
            part sensors : Sensor_0412[2];
            action smooth : Common::Process;
            action forward : Common::Process;
            succession first smooth then forward;
            exhibit state lifecycle : Common::Lifecycle;
        }
        requirement controllerMass_0412 : Common::MassLimit {
            subject component : Controller_0412;
            attribute :>> limit = 2.0 [kg];
        }
    }

    package Subsystem_0413 {
        part def Sensor_0413 :> Common::Component {
            attribute :>> mass = 0.23 [kg];
            attribute :>> cost = 43.0;
            attribute range : Real = 113.0;
            port data : Common::DataPort;
        }
        part def Controller_0413 :> Common::Component {
            attribute :>> mass = 1.00 [kg];
            attribute :>> cost = 213.0;
            port supply : Common::PowerPort;
            part sensors : Sensor_0413[2];
            action smooth : Common::Process;
            action forward : Common::Process;
            succession first smooth then forward;
            exhibit state lifecycle : Common::Lifecycle;
        }
        requirement controllerMass_0413 : Common::MassLimit {
            subject component : Controller_0413;
            attribute :>> limit = 2.0 [kg];
        }
    }

    package Subsystem_0414 {
        part def Sensor_0414 :> Common::Component {
            attribute :>> mass = 0.24 [kg];
            attribute :>> cost = 44.0;
            attribute range : Real = 114.0;
            port data : Common::DataPort;
        }
        part def Controller_0414 :> Common::Component {
            attribute :>> mass = 1.10 [kg];
            attribute :>> cost = 214.0;
            port supply : Common::PowerPort;
            part sensors : Sensor_0414[2];
            action smooth : Common::Process;
            action forward : Common::Process;
            succession first smooth then forward;
            exhibit state lifecycle : Common::Lifecycle;
        }
        requirement controllerMass_0414 : Common::MassLimit {
            subject component : Controller_0414;
            attribute :>> limit = 2.0 [kg];
        }
    }

    package Subsystem_0415 {
        part def Sensor_0415 :> Common::Component {
            attribute :>> mass = 0.20 [kg];
            attribute :>> cost = 45.0;
            attribute range : Real = 115.0;
            port data : Common::DataPort;
        }
        part def Controller_0415 :> Common::Component {
            attribute :>> mass = 1.20 [kg];
            attribute :>> cost = 215.0;
            port supply : Common::PowerPort;
            part sensors : Sensor_0415[2];
            action smooth : Common::Process;
            action forward : Common::Process;
            succession first smooth then forward;
            exhibit state lifecycle : Common::Lifecycle;
        }
        requirement controllerMass_0415 : Common::MassLimit {
            subject component : Controller_0415;
            attribute :>> limit = 2.0 [kg];
        }
    }

    package Subsystem_0416 {
        part def Sensor_0416 :> Common::Component {
            attribute :>> mass = 0.21 [kg];
            attribute :>> cost = 46.0;
            attribute range : Real = 116.0;
            port data : Common::DataPort;
        }
        part def Controller_0416 :> Common::Component {
            attribute :>> mass = 1.30 [kg];
            attribute :>> cost = 216.0;
            port supply : Common::PowerPort;
            part sensors : Sensor_0416[2];
            action smooth : Common::Process;
            action forward : Common::Process;
            succession first smooth then forward;
            exhibit state lifecycle : Common::Lifecycle;
        }
        requirement controllerMass_0416 : Common::MassLimit {
            subject component : Controller_0416;
            attribute :>> limit = 2.0 [kg];
        }
    }

    package Subsystem_0417 {
        part def Sensor_0417 :> Common::Component {
            attribute :>> mass = 0.22 [kg];
            attribute :>> cost = 47.0;
            attribute range : Real = 117.0;
            port data : Common::DataPort;
        }
        part def Controller_0417 :> Common::Component {
            attribute :>> mass = 1.40 [kg];
            attribute :>> cost = 217.0;
            port supply : Common::PowerPort;
            part sensors : Sensor_0417[2];
            action smooth : Common::Process;
            action forward : Common::Process;
            succession first smooth then forward;
            exhibit state lifecycle : Common::Lifecycle;
        }
        requirement controllerMass_0417 : Common::MassLimit {
            subject component : Controller_0417;
            attribute :>> limit = 2.0 [kg];
        }
    }

    package Subsystem_0418 {
        part def Sensor_0418 :> Common::Component {
            attribute :>> mass = 0.23 [kg];
            attribute :>> cost = 48.0;
            attribute range : Real = 118.0;
            port data : Common::DataPort;
        }
        part def Controller_0418 :> Common::Component {
            attribute :>> mass = 1.50 [kg];
            attribute :>> cost = 218.0;
            port supply : Common::PowerPort;
            part sensors : Sensor_0418[2];
            action smooth : Common::Process;
            action forward : Common::Process;
            succession first smooth then forward;
            exhibit state lifecycle : Common::Lifecycle;
        }
        requirement controllerMass_0418 : Common::MassLimit {
            subject component : Controller_0418;
            attribute :>> limit = 2.0 [kg];
        }
    }

    package Subsystem_0419 {
        part def Sensor_0419 :> Common::Component {
            attribute :>> mass = 0.24 [kg];
            attribute :>> cost = 49.0;
            attribute range : Real = 119.0;
            port data : Common::DataPort;
        }
        part def Controller_0419 :> Common::Component {
            attribute :>> mass = 1.60 [kg];
            attribute :>> cost = 219.0;
            port supply : Common::PowerPort;
            part sensors : Sensor_0419[2];
            action smooth : Common::Process;
            action forward : Common::Process;
            succession first smooth then forward;
            exhibit state lifecycle : Common::Lifecycle;
        }
        requirement controllerMass_0419 : Common::MassLimit {
            subject component : Controller_0419;
            attribute :>> limit = 2.0 [kg];
        }
    }

    package Subsystem_0420 {
        part def Sensor_0420 :> Common::Component {
            attribute :>> mass = 0.20 [kg];
            attribute :>> cost = 30.0;
            attribute range : Real = 120.0;
            port data : Common::DataPort;
        }
        part def Controller_0420 :> Common::Component {
            attribute :>> mass = 1.00 [kg];
            attribute :>> cost = 220.0;
            port supply : Common::PowerPort;
            part sensors : Sensor_0420[2];
            action smooth : Common::Process;
            action forward : Common::Process;
            succession first smooth then forward;
            exhibit state lifecycle : Common::Lifecycle;
        }
        requirement controllerMass_0420 : Common::MassLimit {
            subject component : Controller_0420;
            attribute :>> limit = 2.0 [kg];
        }
    }

    package Subsystem_0421 {
        part def Sensor_0421 :> Common::Component {
            attribute :>> mass = 0.21 [kg];
            attribute :>> cost = 31.0;
            attribute range : Real = 121.0;
            port data : Common::DataPort;
        }
        part def Controller_0421 :> Common::Component {
            attribute :>> mass = 1.10 [kg];
            attribute :>> cost = 221.0;
            port supply : Common::PowerPort;
            part sensors : Sensor_0421[2];
            action smooth : Common::Process;
            action forward : Common::Process;
            succession first smooth then forward;
            exhibit state lifecycle : Common::Lifecycle;
        }
        requirement controllerMass_0421 : Common::MassLimit {
            subject component : Controller_0421;
            attribute :>> limit = 2.0 [kg];
        }
    }

    package Subsystem_0422 {
        part def Sensor_0422 :> Common::Component {
            attribute :>> mass = 0.22 [kg];
            attribute :>> cost = 32.0;
            attribute range : Real = 122.0;
            port data : Common::DataPort;
        }
        part def Controller_0422 :> Common::Component {
            attribute :>> mass = 1.20 [kg];
            attribute :>> cost = 222.0;
            port supply : Common::PowerPort;
            part sensors : Sensor_0422[2];
            action smooth : Common::Process;
            action forward : Common::Process;
            succession first smooth then forward;
            exhibit state lifecycle : Common::Lifecycle;
        }
        requirement controllerMass_0422 : Common::MassLimit {
            subject component : Controller_0422;
            attribute :>> limit = 2.0 [kg];
        }
    }

    package Subsystem_0423 {
        part def Sensor_0423 :> Common::Component {
            attribute :>> mass = 0.23 [kg];
            attribute :>> cost = 33.0;
            attribute range : Real = 123.0;
            port data : Common::DataPort;
        }
        part def Controller_0423 :> Common::Component {
            attribute :>> mass = 1.30 [kg];
            attribute :>> cost = 223.0;
            port supply : Common::PowerPort;
            part sensors : Sensor_0423[2];
            action smooth : Common::Process;
            action forward : Common::Process;
            succession first smooth then forward;
            exhibit state lifecycle : Common::Lifecycle;
        }
        requirement controllerMass_0423 : Common::MassLimit {
            subject component : Controller_0423;
            attribute :>> limit = 2.0 [kg];
        }
    }

    package Subsystem_0424 {
        part def Sensor_0424 :> Common::Component {
            attribute :>> mass = 0.24 [kg];
            attribute :>> cost = 34.0;
            attribute range : Real = 124.0;
            port data : Common::DataPort;
        }
        part def Controller_0424 :> Common::Component {
            attribute :>> mass = 1.40 [kg];
            attribute :>> cost = 224.0;
            port supply : Common::PowerPort;
            part sensors : Sensor_0424[2];
            action smooth : Common::Process;
            action forward : Common::Process;
            succession first smooth then forward;
            exhibit state lifecycle : Common::Lifecycle;
        }
        requirement controllerMass_0424 : Common::MassLimit {
            subject component : Controller_0424;
            attribute :>> limit = 2.0 [kg];
        }
    }

    package Subsystem_0425 {
        part def Sensor_0425 :> Common::Component {
            attribute :>> mass = 0.20 [kg];
            attribute :>> cost = 35.0;
            attribute range : Real = 125.0;
            port data : Common::DataPort;
        }
        part def Controller_0425 :> Common::Component {
            attribute :>> mass = 1.50 [kg];
            attribute :>> cost = 225.0;
            port supply : Common::PowerPort;
            part sensors : Sensor_0425[2];
            action smooth : Common::Process;
            action forward : Common::Process;
            succession first smooth then forward;
            exhibit state lifecycle : Common::Lifecycle;
        }
        requirement controllerMass_0425 : Common::MassLimit {
            subject component : Controller_0425;
            attribute :>> limit = 2.0 [kg];
        }
    }

    package Subsystem_0426 {
        part def Sensor_0426 :> Common::Component {
            attribute :>> mass = 0.21 [kg];
            attribute :>> cost = 36.0;
            attribute range : Real = 126.0;
            port data : Common::DataPort;
        }
        part def Controller_0426 :> Common::Component {
            attribute :>> mass = 1.60 [kg];
            attribute :>> cost = 226.0;
            port supply : Common::PowerPort;
            part sensors : Sensor_0426[2];
            action smooth : Common::Process;
            action forward : Common::Process;
            succession first smooth then forward;
            exhibit state lifecycle : Common::Lifecycle;
        }
        requirement controllerMass_0426 : Common::MassLimit {
            subject component : Controller_0426;
            attribute :>> limit = 2.0 [kg];
        }
    }

    package Subsystem_0427 {
        part def Sensor_0427 :> Common::Component {
            attribute :>> mass = 0.22 [kg];
            attribute :>> cost = 37.0;
            attribute range : Real = 127.0;
            port data : Common::DataPort;
        }
        part def Controller_0427 :> Common::Component {
            attribute :>> mass = 1.00 [kg];
            attribute :>> cost = 227.0;
            port supply : Common::PowerPort;
            part sensors : Sensor_0427[2];
            action smooth : Common::Process;
            action forward : Common::Process;
            succession first smooth then forward;
            exhibit state lifecycle : Common::Lifecycle;
        }
        requirement controllerMass_0427 : Common::MassLimit {
            subject component : Controller_0427;
            attribute :>> limit = 2.0 [kg];
        }
    }

    package Subsystem_0428 {
        part def Sensor_0428 :> Common::Component {
            attribute :>> mass = 0.23 [kg];
            attribute :>> cost = 38.0;
            attribute range : Real = 128.0;
            port data : Common::DataPort;
        }
        part def Controller_0428 :> Common::Component {
            attribute :>> mass = 1.10 [kg];
            attribute :>> cost = 228.0;
            port supply : Common::PowerPort;
            part sensors : Sensor_0428[2];
            action smooth : Common::Process;
            action forward : Common::Process;
            succession first smooth then forward;
            exhibit state lifecycle : Common::Lifecycle;
        }
        requirement controllerMass_0428 : Common::MassLimit {
            subject component : Controller_0428;
            attribute :>> limit = 2.0 [kg];
        }
    }

    package Subsystem_0429 {
        part def Sensor_0429 :> Common::Component {
            attribute :>> mass = 0.24 [kg];
            attribute :>> cost = 39.0;
            attribute range : Real = 129.0;
            port data : Common::DataPort;
        }
        part def Controller_0429 :> Common::Component {
            attribute :>> mass = 1.20 [kg];
            attribute :>> cost = 229.0;
            port supply : Common::PowerPort;
            part sensors : Sensor_0429[2];
            action smooth : Common::Process;
            action forward : Common::Process;
            succession first smooth then forward;
            exhibit state lifecycle : Common::Lifecycle;
        }
        requirement controllerMass_0429 : Common::MassLimit {
            subject component : Controller_0429;
            attribute :>> limit = 2.0 [kg];
        }
    }

    package Subsystem_0430 {
        part def Sensor_0430 :> Common::Component {
            attribute :>> mass = 0.20 [kg];
            attribute :>> cost = 40.0;
            attribute range : Real = 130.0;
            port data : Common::DataPort;
        }
        part def Controller_0430 :> Common::Component {
            attribute :>> mass = 1.30 [kg];
            attribute :>> cost = 230.0;
            port supply : Common::PowerPort;
            part sensors : Sensor_0430[2];
            action smooth : Common::Process;
            action forward : Common::Process;
            succession first smooth then forward;
            exhibit state lifecycle : Common::Lifecycle;
        }
        requirement controllerMass_0430 : Common::MassLimit {
            subject component : Controller_0430;
            attribute :>> limit = 2.0 [kg];
        }
    }

    package Subsystem_0431 {
        part def Sensor_0431 :> Common::Component {
            attribute :>> mass = 0.21 [kg];
            attribute :>> cost = 41.0;
            attribute range : Real = 131.0;
            port data : Common::DataPort;
        }
        part def Controller_0431 :> Common::Component {
            attribute :>> mass = 1.40 [kg];
            attribute :>> cost = 231.0;
            port supply : Common::PowerPort;
            part sensors : Sensor_0431[2];
            action smooth : Common::Process;
            action forward : Common::Process;
            succession first smooth then forward;
            exhibit state lifecycle : Common::Lifecycle;
        }
        requirement controllerMass_0431 : Common::MassLimit {
            subject component : Controller_0431;
            attribute :>> limit = 2.0 [kg];
        }
    }

    package Subsystem_0432 {
        part def Sensor_0432 :> Common::Component {
            attribute :>> mass = 0.22 [kg];
            attribute :>> cost = 42.0;
            attribute range : Real = 132.0;
            port data : Common::DataPort;
        }
        part def Controller_0432 :> Common::Component {
            attribute :>> mass = 1.50 [kg];
            attribute :>> cost = 232.0;
            port supply : Common::PowerPort;
            part sensors : Sensor_0432[2];
            action smooth : Common::Process;
            action forward : Common::Process;
            succession first smooth then forward;
            exhibit state lifecycle : Common::Lifecycle;
        }
        requirement controllerMass_0432 : Common::MassLimit {
            subject component : Controller_0432;
            attribute :>> limit = 2.0 [kg];
        }
    }

    package Subsystem_0433 {
        part def Sensor_0433 :> Common::Component {
            attribute :>> mass = 0.23 [kg];
            attribute :>> cost = 43.0;
            attribute range : Real = 133.0;
            port data : Common::DataPort;
        }
        part def Controller_0433 :> Common::Component {
            attribute :>> mass = 1.60 [kg];
            attribute :>> cost = 233.0;
            port supply : Common::PowerPort;
            part sensors : Sensor_0433[2];
            action smooth : Common::Process;
            action forward : Common::Process;
            succession first smooth then forward;
            exhibit state lifecycle : Common::Lifecycle;
        }
        requirement controllerMass_0433 : Common::MassLimit {
            subject component : Controller_0433;
            attribute :>> limit = 2.0 [kg];
        }
    }

    package Subsystem_0434 {
        part def Sensor_0434 :> Common::Component {
            attribute :>> mass = 0.24 [kg];
            attribute :>> cost = 44.0;
            attribute range : Real = 134.0;
            port data : Common::DataPort;
        }
        part def Controller_0434 :> Common::Component {
            attribute :>> mass = 1.00 [kg];
            attribute :>> cost = 234.0;
            port supply : Common::PowerPort;
            part sensors : Sensor_0434[2];
            action smooth : Common::Process;
            action forward : Common::Process;
            succession first smooth then forward;
            exhibit state lifecycle : Common::Lifecycle;
        }
        requirement controllerMass_0434 : Common::MassLimit {
            subject component : Controller_0434;
            attribute :>> limit = 2.0 [kg];
        }
    }

    package Subsystem_0435 {
        part def Sensor_0435 :> Common::Component {
            attribute :>> mass = 0.20 [kg];
            attribute :>> cost = 45.0;
            attribute range : Real = 135.0;
            port data : Common::DataPort;
        }
        part def Controller_0435 :> Common::Component {
            attribute :>> mass = 1.10 [kg];
            attribute :>> cost = 235.0;
            port supply : Common::PowerPort;
            part sensors : Sensor_0435[2];
            action smooth : Common::Process;
            action forward : Common::Process;
            succession first smooth then forward;
            exhibit state lifecycle : Common::Lifecycle;
        }
        requirement controllerMass_0435 : Common::MassLimit {
            subject component : Controller_0435;
            attribute :>> limit = 2.0 [kg];
        }
    }

    package Subsystem_0436 {
        part def Sensor_0436 :> Common::Component {
            attribute :>> mass = 0.21 [kg];
            attribute :>> cost = 46.0;
            attribute range : Real = 136.0;
            port data : Common::DataPort;
        }
        part def Controller_0436 :> Common::Component {
            attribute :>> mass = 1.20 [kg];
            attribute :>> cost = 236.0;
            port supply : Common::PowerPort;
            part sensors : Sensor_0436[2];
            action smooth : Common::Process;
            action forward : Common::Process;
            succession first smooth then forward;
            exhibit state lifecycle : Common::Lifecycle;
        }
        requirement controllerMass_0436 : Common::MassLimit {
            subject component : Controller_0436;
            attribute :>> limit = 2.0 [kg];
        }
    }

    package Subsystem_0437 {
        part def Sensor_0437 :> Common::Component {
            attribute :>> mass = 0.22 [kg];
            attribute :>> cost = 47.0;
            attribute range : Real = 137.0;
            port data : Common::DataPort;
        }
        part def Controller_0437 :> Common::Component {
            attribute :>> mass = 1.30 [kg];
            attribute :>> cost = 237.0;
            port supply : Common::PowerPort;
            part sensors : Sensor_0437[2];
            action smooth : Common::Process;
            action forward : Common::Process;
            succession first smooth then forward;
            exhibit state lifecycle : Common::Lifecycle;
        }
        requirement controllerMass_0437 : Common::MassLimit {
            subject component : Controller_0437;
            attribute :>> limit = 2.0 [kg];
        }
    }

    package Subsystem_0438 {
        part def Sensor_0438 :> Common::Component {
            attribute :>> mass = 0.23 [kg];
            attribute :>> cost = 48.0;
            attribute range : Real = 138.0;
            port data : Common::DataPort;
        }
        part def Controller_0438 :> Common::Component {
            attribute :>> mass = 1.40 [kg];
            attribute :>> cost = 238.0;
            port supply : Common::PowerPort;
            part sensors : Sensor_0438[2];
            action smooth : Common::Process;
            action forward : Common::Process;
            succession first smooth then forward;
            exhibit state lifecycle : Common::Lifecycle;
        }
        requirement controllerMass_0438 : Common::MassLimit {
            subject component : Controller_0438;
            attribute :>> limit = 2.0 [kg];
        }
    }

    package Subsystem_0439 {
        part def Sensor_0439 :> Common::Component {
            attribute :>> mass = 0.24 [kg];
            attribute :>> cost = 49.0;
            attribute range : Real = 139.0;
            port data : Common::DataPort;
        }
        part def Controller_0439 :> Common::Component {
            attribute :>> mass = 1.50 [kg];
            attribute :>> cost = 239.0;
            port supply : Common::PowerPort;
            part sensors : Sensor_0439[2];
            action smooth : Common::Process;
            action forward : Common::Process;
            succession first smooth then forward;
            exhibit state lifecycle : Common::Lifecycle;
        }
        requirement controllerMass_0439 : Common::MassLimit {
            subject component : Controller_0439;
            attribute :>> limit = 2.0 [kg];
        }
    }

    package Subsystem_0440 {
        part def Sensor_0440 :> Common::Component {
            attribute :>> mass = 0.20 [kg];
            attribute :>> cost = 30.0;
            attribute range : Real = 140.0;
            port data : Common::DataPort;
        }
        part def Controller_0440 :> Common::Component {
            attribute :>> mass = 1.60 [kg];
            attribute :>> cost = 240.0;
            port supply : Common::PowerPort;
            part sensors : Sensor_0440[2];
            action smooth : Common::Process;
            action forward : Common::Process;
            succession first smooth then forward;
            exhibit state lifecycle : Common::Lifecycle;
        }
        requirement controllerMass_0440 : Common::MassLimit {
            subject component : Controller_0440;
            attribute :>> limit = 2.0 [kg];
        }
    }

    package Subsystem_0441 {
        part def Sensor_0441 :> Common::Component {
            attribute :>> mass = 0.21 [kg];
            attribute :>> cost = 31.0;
            attribute range : Real = 141.0;
            port data : Common::DataPort;
        }
        part def Controller_0441 :> Common::Component {
            attribute :>> mass = 1.00 [kg];
            attribute :>> cost = 241.0;
            port supply : Common::PowerPort;
            part sensors : Sensor_0441[2];
            action smooth : Common::Process;
            action forward : Common::Process;
            succession first smooth then forward;
            exhibit state lifecycle : Common::Lifecycle;
        }
        requirement controllerMass_0441 : Common::MassLimit {
            subject component : Controller_0441;
            attribute :>> limit = 2.0 [kg];
        }
    }

    package Subsystem_0442 {
        part def Sensor_0442 :> Common::Component {
            attribute :>> mass = 0.22 [kg];
            attribute :>> cost = 32.0;
            attribute range : Real = 142.0;
            port data : Common::DataPort;
        }
        part def Controller_0442 :> Common::Component {
            attribute :>> mass = 1.10 [kg];
            attribute :>> cost = 242.0;
            port supply : Common::PowerPort;
            part sensors : Sensor_0442[2];
            action smooth : Common::Process;
            action forward : Common::Process;
            succession first smooth then forward;
            exhibit state lifecycle : Common::Lifecycle;
        }
        requirement controllerMass_0442 : Common::MassLimit {
            subject component : Controller_0442;
            attribute :>> limit = 2.0 [kg];
        }
    }

    package Subsystem_0443 {
        part def Sensor_0443 :> Common::Component {
            attribute :>> mass = 0.23 [kg];
            attribute :>> cost = 33.0;
            attribute range : Real = 143.0;
            port data : Common::DataPort;
        }
        part def Controller_0443 :> Common::Component {
            attribute :>> mass = 1.20 [kg];
            attribute :>> cost = 243.0;
            port supply : Common::PowerPort;
            part sensors : Sensor_0443[2];
            action smooth : Common::Process;
            action forward : Common::Process;
            succession first smooth then forward;
            exhibit state lifecycle : Common::Lifecycle;
        }
        requirement controllerMass_0443 : Common::MassLimit {
            subject component : Controller_0443;
            attribute :>> limit = 2.0 [kg];
        }
    }

    package Subsystem_0444 {
        part def Sensor_0444 :> Common::Component {
            attribute :>> mass = 0.24 [kg];
            attribute :>> cost = 34.0;
            attribute range : Real = 144.0;
            port data : Common::DataPort;
        }
        part def Controller_0444 :> Common::Component {
            attribute :>> mass = 1.30 [kg];
            attribute :>> cost = 244.0;
            port supply : Common::PowerPort;
            part sensors : Sensor_0444[2];
            action smooth : Common::Process;
            action forward : Common::Process;
            succession first smooth then forward;
            exhibit state lifecycle : Common::Lifecycle;
        }
        requirement controllerMass_0444 : Common::MassLimit {
            subject component : Controller_0444;
            attribute :>> limit = 2.0 [kg];
        }
    }

    package Subsystem_0445 {
        part def Sensor_0445 :> Common::Component {
            attribute :>> mass = 0.20 [kg];
            attribute :>> cost = 35.0;
            attribute range : Real = 145.0;
            port data : Common::DataPort;
        }
        part def Controller_0445 :> Common::Component {
            attribute :>> mass = 1.40 [kg];
            attribute :>> cost = 245.0;
            port supply : Common::PowerPort;
            part sensors : Sensor_0445[2];
            action smooth : Common::Process;
            action forward : Common::Process;
            succession first smooth then forward;
            exhibit state lifecycle : Common::Lifecycle;
        }
        requirement controllerMass_0445 : Common::MassLimit {
            subject component : Controller_0445;
            attribute :>> limit = 2.0 [kg];
        }
    }

    package Subsystem_0446 {
        part def Sensor_0446 :> Common::Component {
            attribute :>> mass = 0.21 [kg];
            attribute :>> cost = 36.0;
            attribute range : Real = 146.0;
            port data : Common::DataPort;
        }
        part def Controller_0446 :> Common::Component {
            attribute :>> mass = 1.50 [kg];
            attribute :>> cost = 246.0;
            port supply : Common::PowerPort;
            part sensors : Sensor_0446[2];
            action smooth : Common::Process;
            action forward : Common::Process;
            succession first smooth then forward;
            exhibit state lifecycle : Common::Lifecycle;
        }
        requirement controllerMass_0446 : Common::MassLimit {
            subject component : Controller_0446;
            attribute :>> limit = 2.0 [kg];
        }
    }

    package Subsystem_0447 {
        part def Sensor_0447 :> Common::Component {
            attribute :>> mass = 0.22 [kg];
            attribute :>> cost = 37.0;
            attribute range : Real = 147.0;
            port data : Common::DataPort;
        }
        part def Controller_0447 :> Common::Component {
            attribute :>> mass = 1.60 [kg];
            attribute :>> cost = 247.0;
            port supply : Common::PowerPort;
            part sensors : Sensor_0447[2];
            action smooth : Common::Process;
            action forward : Common::Process;
            succession first smooth then forward;
            exhibit state lifecycle : Common::Lifecycle;
        }
        requirement controllerMass_0447 : Common::MassLimit {
            subject component : Controller_0447;
            attribute :>> limit = 2.0 [kg];
        }
    }

    package Subsystem_0448 {
        part def Sensor_0448 :> Common::Component {
            attribute :>> mass = 0.23 [kg];
            attribute :>> cost = 38.0;
            attribute range : Real = 148.0;
            port data : Common::DataPort;
        }
        part def Controller_0448 :> Common::Component {
            attribute :>> mass = 1.00 [kg];
            attribute :>> cost = 248.0;
            port supply : Common::PowerPort;
            part sensors : Sensor_0448[2];
            action smooth : Common::Process;
            action forward : Common::Process;
            succession first smooth then forward;
            exhibit state lifecycle : Common::Lifecycle;
        }
        requirement controllerMass_0448 : Common::MassLimit {
            subject component : Controller_0448;
            attribute :>> limit = 2.0 [kg];
        }
    }

    package Subsystem_0449 {
        part def Sensor_0449 :> Common::Component {
            attribute :>> mass = 0.24 [kg];
            attribute :>> cost = 39.0;
            attribute range : Real = 149.0;
            port data : Common::DataPort;
        }
        part def Controller_0449 :> Common::Component {
            attribute :>> mass = 1.10 [kg];
            attribute :>> cost = 249.0;
            port supply : Common::PowerPort;
            part sensors : Sensor_0449[2];
            action smooth : Common::Process;
            action forward : Common::Process;
            succession first smooth then forward;
            exhibit state lifecycle : Common::Lifecycle;
        }
        requirement controllerMass_0449 : Common::MassLimit {
            subject component : Controller_0449;
            attribute :>> limit = 2.0 [kg];
        }
    }

    package Subsystem_0450 {
        part def Sensor_0450 :> Common::Component {
            attribute :>> mass = 0.20 [kg];
            attribute :>> cost = 40.0;
            attribute range : Real = 100.0;
            port data : Common::DataPort;
        }
        part def Controller_0450 :> Common::Component {
            attribute :>> mass = 1.20 [kg];
            attribute :>> cost = 250.0;
            port supply : Common::PowerPort;
            part sensors : Sensor_0450[2];
            action smooth : Common::Process;
            action forward : Common::Process;
            succession first smooth then forward;
            exhibit state lifecycle : Common::Lifecycle;
        }
        requirement controllerMass_0450 : Common::MassLimit {
            subject component : Controller_0450;
            attribute :>> limit = 2.0 [kg];
        }
    }

    package Subsystem_0451 {
        part def Sensor_0451 :> Common::Component {
            attribute :>> mass = 0.21 [kg];
            attribute :>> cost = 41.0;
            attribute range : Real = 101.0;
            port data : Common::DataPort;
        }
        part def Controller_0451 :> Common::Component {
            attribute :>> mass = 1.30 [kg];
            attribute :>> cost = 251.0;
            port supply : Common::PowerPort;
            part sensors : Sensor_0451[2];
            action smooth : Common::Process;
            action forward : Common::Process;
            succession first smooth then forward;
            exhibit state lifecycle : Common::Lifecycle;
        }
        requirement controllerMass_0451 : Common::MassLimit {
            subject component : Controller_0451;
            attribute :>> limit = 2.0 [kg];
        }
    }

    package Subsystem_0452 {
        part def Sensor_0452 :> Common::Component {
            attribute :>> mass = 0.22 [kg];
            attribute :>> cost = 42.0;
            attribute range : Real = 102.0;
            port data : Common::DataPort;
        }
        part def Controller_0452 :> Common::Component {
            attribute :>> mass = 1.40 [kg];
            attribute :>> cost = 252.0;
            port supply : Common::PowerPort;
            part sensors : Sensor_0452[2];
            action smooth : Common::Process;
            action forward : Common::Process;
            succession first smooth then forward;
            exhibit state lifecycle : Common::Lifecycle;
        }
        requirement controllerMass_0452 : Common::MassLimit {
            subject component : Controller_0452;
            attribute :>> limit = 2.0 [kg];
        }
    }

    package Subsystem_0453 {
        part def Sensor_0453 :> Common::Component {
            attribute :>> mass = 0.23 [kg];
            attribute :>> cost = 43.0;
            attribute range : Real = 103.0;
            port data : Common::DataPort;
        }
        part def Controller_0453 :> Common::Component {
            attribute :>> mass = 1.50 [kg];
            attribute :>> cost = 253.0;
            port supply : Common::PowerPort;
            part sensors : Sensor_0453[2];
            action smooth : Common::Process;
            action forward : Common::Process;
            succession first smooth then forward;
            exhibit state lifecycle : Common::Lifecycle;
        }
        requirement controllerMass_0453 : Common::MassLimit {
            subject component : Controller_0453;
            attribute :>> limit = 2.0 [kg];
        }
    }

    package Subsystem_0454 {
        part def Sensor_0454 :> Common::Component {
            attribute :>> mass = 0.24 [kg];
            attribute :>> cost = 44.0;
            attribute range : Real = 104.0;
            port data : Common::DataPort;
        }
        part def Controller_0454 :> Common::Component {
            attribute :>> mass = 1.60 [kg];
            attribute :>> cost = 254.0;
            port supply : Common::PowerPort;
            part sensors : Sensor_0454[2];
            action smooth : Common::Process;
            action forward : Common::Process;
            succession first smooth then forward;
            exhibit state lifecycle : Common::Lifecycle;
        }
        requirement controllerMass_0454 : Common::MassLimit {
            subject component : Controller_0454;
            attribute :>> limit = 2.0 [kg];
        }
    }

    package Subsystem_0455 {
        part def Sensor_0455 :> Common::Component {
            attribute :>> mass = 0.20 [kg];
            attribute :>> cost = 45.0;
            attribute range : Real = 105.0;
            port data : Common::DataPort;
        }
        part def Controller_0455 :> Common::Component {
            attribute :>> mass = 1.00 [kg];
            attribute :>> cost = 255.0;
            port supply : Common::PowerPort;
            part sensors : Sensor_0455[2];
            action smooth : Common::Process;
            action forward : Common::Process;
            succession first smooth then forward;
            exhibit state lifecycle : Common::Lifecycle;
        }
        requirement controllerMass_0455 : Common::MassLimit {
            subject component : Controller_0455;
            attribute :>> limit = 2.0 [kg];
        }
    }

    package Subsystem_0456 {
        part def Sensor_0456 :> Common::Component {
            attribute :>> mass = 0.21 [kg];
            attribute :>> cost = 46.0;
            attribute range : Real = 106.0;
            port data : Common::DataPort;
        }
        part def Controller_0456 :> Common::Component {
            attribute :>> mass = 1.10 [kg];
            attribute :>> cost = 256.0;
            port supply : Common::PowerPort;
            part sensors : Sensor_0456[2];
            action smooth : Common::Process;
            action forward : Common::Process;
            succession first smooth then forward;
            exhibit state lifecycle : Common::Lifecycle;
        }
        requirement controllerMass_0456 : Common::MassLimit {
            subject component : Controller_0456;
            attribute :>> limit = 2.0 [kg];
        }
    }

    package Subsystem_0457 {
        part def Sensor_0457 :> Common::Component {
            attribute :>> mass = 0.22 [kg];
            attribute :>> cost = 47.0;
            attribute range : Real = 107.0;
            port data : Common::DataPort;
        }
        part def Controller_0457 :> Common::Component {
            attribute :>> mass = 1.20 [kg];
            attribute :>> cost = 257.0;
            port supply : Common::PowerPort;
            part sensors : Sensor_0457[2];
            action smooth : Common::Process;
            action forward : Common::Process;
            succession first smooth then forward;
            exhibit state lifecycle : Common::Lifecycle;
        }
        requirement controllerMass_0457 : Common::MassLimit {
            subject component : Controller_0457;
            attribute :>> limit = 2.0 [kg];
        }
    }

    package Subsystem_0458 {
        part def Sensor_0458 :> Common::Component {
            attribute :>> mass = 0.23 [kg];
            attribute :>> cost = 48.0;
            attribute range : Real = 108.0;
            port data : Common::DataPort;
        }
        part def Controller_0458 :> Common::Component {
            attribute :>> mass = 1.30 [kg];
            attribute :>> cost = 258.0;
            port supply : Common::PowerPort;
            part sensors : Sensor_0458[2];
            action smooth : Common::Process;
            action forward : Common::Process;
            succession first smooth then forward;
            exhibit state lifecycle : Common::Lifecycle;
        }
        requirement controllerMass_0458 : Common::MassLimit {
            subject component : Controller_0458;
            attribute :>> limit = 2.0 [kg];
        }
    }

    package Subsystem_0459 {
        part def Sensor_0459 :> Common::Component {
            attribute :>> mass = 0.24 [kg];
            attribute :>> cost = 49.0;
            attribute range : Real = 109.0;
            port data : Common::DataPort;
        }
        part def Controller_0459 :> Common::Component {
            attribute :>> mass = 1.40 [kg];
            attribute :>> cost = 259.0;
            port supply : Common::PowerPort;
            part sensors : Sensor_0459[2];
            action smooth : Common::Process;
            action forward : Common::Process;
            succession first smooth then forward;
            exhibit state lifecycle : Common::Lifecycle;
        }
        requirement controllerMass_0459 : Common::MassLimit {
            subject component : Controller_0459;
            attribute :>> limit = 2.0 [kg];
        }
    }

    package Subsystem_0460 {
        part def Sensor_0460 :> Common::Component {
            attribute :>> mass = 0.20 [kg];
            attribute :>> cost = 30.0;
            attribute range : Real = 110.0;
            port data : Common::DataPort;
        }
        part def Controller_0460 :> Common::Component {
            attribute :>> mass = 1.50 [kg];
            attribute :>> cost = 260.0;
            port supply : Common::PowerPort;
            part sensors : Sensor_0460[2];
            action smooth : Common::Process;
            action forward : Common::Process;
            succession first smooth then forward;
            exhibit state lifecycle : Common::Lifecycle;
        }
        requirement controllerMass_0460 : Common::MassLimit {
            subject component : Controller_0460;
            attribute :>> limit = 2.0 [kg];
        }
    }

    package Subsystem_0461 {
        part def Sensor_0461 :> Common::Component {
            attribute :>> mass = 0.21 [kg];
            attribute :>> cost = 31.0;
            attribute range : Real = 111.0;
            port data : Common::DataPort;
        }
        part def Controller_0461 :> Common::Component {
            attribute :>> mass = 1.60 [kg];
            attribute :>> cost = 261.0;
            port supply : Common::PowerPort;
            part sensors : Sensor_0461[2];
            action smooth : Common::Process;
            action forward : Common::Process;
            succession first smooth then forward;
            exhibit state lifecycle : Common::Lifecycle;
        }
        requirement controllerMass_0461 : Common::MassLimit {
            subject component : Controller_0461;
            attribute :>> limit = 2.0 [kg];
        }
    }

    package Subsystem_0462 {
        part def Sensor_0462 :> Common::Component {
            attribute :>> mass = 0.22 [kg];
            attribute :>> cost = 32.0;
            attribute range : Real = 112.0;
            port data : Common::DataPort;
        }
        part def Controller_0462 :> Common::Component {
            attribute :>> mass = 1.00 [kg];
            attribute :>> cost = 262.0;
            port supply : Common::PowerPort;
            part sensors : Sensor_0462[2];
            action smooth : Common::Process;
            action forward : Common::Process;
            succession first smooth then forward;
            exhibit state lifecycle : Common::Lifecycle;
        }
        requirement controllerMass_0462 : Common::MassLimit {
            subject component : Controller_0462;
            attribute :>> limit = 2.0 [kg];
        }
    }

    package Subsystem_0463 {
        part def Sensor_0463 :> Common::Component {
            attribute :>> mass = 0.23 [kg];
            attribute :>> cost = 33.0;
            attribute range : Real = 113.0;
            port data : Common::DataPort;
        }
        part def Controller_0463 :> Common::Component {
            attribute :>> mass = 1.10 [kg];
            attribute :>> cost = 263.0;
            port supply : Common::PowerPort;
            part sensors : Sensor_0463[2];
            action smooth : Common::Process;
            action forward : Common::Process;
            succession first smooth then forward;
            exhibit state lifecycle : Common::Lifecycle;
        }
        requirement controllerMass_0463 : Common::MassLimit {
            subject component : Controller_0463;
            attribute :>> limit = 2.0 [kg];
        }
    }

    package Subsystem_0464 {
        part def Sensor_0464 :> Common::Component {
            attribute :>> mass = 0.24 [kg];
            attribute :>> cost = 34.0;
            attribute range : Real = 114.0;
            port data : Common::DataPort;
        }
        part def Controller_0464 :> Common::Component {
            attribute :>> mass = 1.20 [kg];
            attribute :>> cost = 264.0;
            port supply : Common::PowerPort;
            part sensors : Sensor_0464[2];
            action smooth : Common::Process;
            action forward : Common::Process;
            succession first smooth then forward;
            exhibit state lifecycle : Common::Lifecycle;
        }
        requirement controllerMass_0464 : Common::MassLimit {
            subject component : Controller_0464;
            attribute :>> limit = 2.0 [kg];
        }
    }

    package Subsystem_0465 {
        part def Sensor_0465 :> Common::Component {
            attribute :>> mass = 0.20 [kg];
            attribute :>> cost = 35.0;
            attribute range : Real = 115.0;
            port data : Common::DataPort;
        }
        part def Controller_0465 :> Common::Component {
            attribute :>> mass = 1.30 [kg];
            attribute :>> cost = 265.0;
            port supply : Common::PowerPort;
            part sensors : Sensor_0465[2];
            action smooth : Common::Process;
            action forward : Common::Process;
            succession first smooth then forward;
            exhibit state lifecycle : Common::Lifecycle;
        }
        requirement controllerMass_0465 : Common::MassLimit {
            subject component : Controller_0465;
            attribute :>> limit = 2.0 [kg];
        }
    }

    package Subsystem_0466 {
        part def Sensor_0466 :> Common::Component {
            attribute :>> mass = 0.21 [kg];
            attribute :>> cost = 36.0;
            attribute range : Real = 116.0;
            port data : Common::DataPort;
        }
        part def Controller_0466 :> Common::Component {
            attribute :>> mass = 1.40 [kg];
            attribute :>> cost = 266.0;
            port supply : Common::PowerPort;
            part sensors : Sensor_0466[2];
            action smooth : Common::Process;
            action forward : Common::Process;
            succession first smooth then forward;
            exhibit state lifecycle : Common::Lifecycle;
        }
        requirement controllerMass_0466 : Common::MassLimit {
            subject component : Controller_0466;
            attribute :>> limit = 2.0 [kg];
        }
    }

    package Subsystem_0467 {
        part def Sensor_0467 :> Common::Component {
            attribute :>> mass = 0.22 [kg];
            attribute :>> cost = 37.0;
            attribute range : Real = 117.0;
            port data : Common::DataPort;
        }
        part def Controller_0467 :> Common::Component {
            attribute :>> mass = 1.50 [kg];
            attribute :>> cost = 267.0;
            port supply : Common::PowerPort;
            part sensors : Sensor_0467[2];
            action smooth : Common::Process;
            action forward : Common::Process;
            succession first smooth then forward;
            exhibit state lifecycle : Common::Lifecycle;
        }
        requirement controllerMass_0467 : Common::MassLimit {
            subject component : Controller_0467;
            attribute :>> limit = 2.0 [kg];
        }
    }

    package Subsystem_0468 {
        part def Sensor_0468 :> Common::Component {
            attribute :>> mass = 0.23 [kg];
            attribute :>> cost = 38.0;
            attribute range : Real = 118.0;
            port data : Common::DataPort;
        }
        part def Controller_0468 :> Common::Component {
            attribute :>> mass = 1.60 [kg];
            attribute :>> cost = 268.0;
            port supply : Common::PowerPort;
            part sensors : Sensor_0468[2];
            action smooth : Common::Process;
            action forward : Common::Process;
            succession first smooth then forward;
            exhibit state lifecycle : Common::Lifecycle;
        }
        requirement controllerMass_0468 : Common::MassLimit {
            subject component : Controller_0468;
            attribute :>> limit = 2.0 [kg];
        }
    }

    package Subsystem_0469 {
        part def Sensor_0469 :> Common::Component {
            attribute :>> mass = 0.24 [kg];
            attribute :>> cost = 39.0;
            attribute range : Real = 119.0;
            port data : Common::DataPort;
        }
        part def Controller_0469 :> Common::Component {
            attribute :>> mass = 1.00 [kg];
            attribute :>> cost = 269.0;
            port supply : Common::PowerPort;
            part sensors : Sensor_0469[2];
            action smooth : Common::Process;
            action forward : Common::Process;
            succession first smooth then forward;
            exhibit state lifecycle : Common::Lifecycle;
        }
        requirement controllerMass_0469 : Common::MassLimit {
            subject component : Controller_0469;
            attribute :>> limit = 2.0 [kg];
        }
    }

    package Subsystem_0470 {
        part def Sensor_0470 :> Common::Component {
            attribute :>> mass = 0.20 [kg];
            attribute :>> cost = 40.0;
            attribute range : Real = 120.0;
            port data : Common::DataPort;
        }
        part def Controller_0470 :> Common::Component {
            attribute :>> mass = 1.10 [kg];
            attribute :>> cost = 270.0;
            port supply : Common::PowerPort;
            part sensors : Sensor_0470[2];
            action smooth : Common::Process;
            action forward : Common::Process;
            succession first smooth then forward;
            exhibit state lifecycle : Common::Lifecycle;
        }
        requirement controllerMass_0470 : Common::MassLimit {
            subject component : Controller_0470;
            attribute :>> limit = 2.0 [kg];
        }
    }

    package Subsystem_0471 {
        part def Sensor_0471 :> Common::Component {
            attribute :>> mass = 0.21 [kg];
            attribute :>> cost = 41.0;
            attribute range : Real = 121.0;
            port data : Common::DataPort;
        }
        part def Controller_0471 :> Common::Component {
            attribute :>> mass = 1.20 [kg];
            attribute :>> cost = 271.0;
            port supply : Common::PowerPort;
            part sensors : Sensor_0471[2];
            action smooth : Common::Process;
            action forward : Common::Process;
            succession first smooth then forward;
            exhibit state lifecycle : Common::Lifecycle;
        }
        requirement controllerMass_0471 : Common::MassLimit {
            subject component : Controller_0471;
            attribute :>> limit = 2.0 [kg];
        }
    }

    package Subsystem_0472 {
        part def Sensor_0472 :> Common::Component {
            attribute :>> mass = 0.22 [kg];
            attribute :>> cost = 42.0;
            attribute range : Real = 122.0;
            port data : Common::DataPort;
        }
        part def Controller_0472 :> Common::Component {
            attribute :>> mass = 1.30 [kg];
            attribute :>> cost = 272.0;
            port supply : Common::PowerPort;
            part sensors : Sensor_0472[2];
            action smooth : Common::Process;
            action forward : Common::Process;
            succession first smooth then forward;
            exhibit state lifecycle : Common::Lifecycle;
        }
        requirement controllerMass_0472 : Common::MassLimit {
            subject component : Controller_0472;
            attribute :>> limit = 2.0 [kg];
        }
    }

    package Subsystem_0473 {
        part def Sensor_0473 :> Common::Component {
            attribute :>> mass = 0.23 [kg];
            attribute :>> cost = 43.0;
            attribute range : Real = 123.0;
            port data : Common::DataPort;
        }
        part def Controller_0473 :> Common::Component {
            attribute :>> mass = 1.40 [kg];
            attribute :>> cost = 273.0;
            port supply : Common::PowerPort;
            part sensors : Sensor_0473[2];
            action smooth : Common::Process;
            action forward : Common::Process;
            succession first smooth then forward;
            exhibit state lifecycle : Common::Lifecycle;
        }
        requirement controllerMass_0473 : Common::MassLimit {
            subject component : Controller_0473;
            attribute :>> limit = 2.0 [kg];
        }
    }

    package Subsystem_0474 {
        part def Sensor_0474 :> Common::Component {
            attribute :>> mass = 0.24 [kg];
            attribute :>> cost = 44.0;
            attribute range : Real = 124.0;
            port data : Common::DataPort;
        }
        part def Controller_0474 :> Common::Component {
            attribute :>> mass = 1.50 [kg];
            attribute :>> cost = 274.0;
            port supply : Common::PowerPort;
            part sensors : Sensor_0474[2];
            action smooth : Common::Process;
            action forward : Common::Process;
            succession first smooth then forward;
            exhibit state lifecycle : Common::Lifecycle;
        }
        requirement controllerMass_0474 : Common::MassLimit {
            subject component : Controller_0474;
            attribute :>> limit = 2.0 [kg];
        }
    }

    package Subsystem_0475 {
        part def Sensor_0475 :> Common::Component {
            attribute :>> mass = 0.20 [kg];
            attribute :>> cost = 45.0;
            attribute range : Real = 125.0;
            port data : Common::DataPort;
        }
        part def Controller_0475 :> Common::Component {
            attribute :>> mass = 1.60 [kg];
            attribute :>> cost = 275.0;
            port supply : Common::PowerPort;
            part sensors : Sensor_0475[2];
            action smooth : Common::Process;
            action forward : Common::Process;
            succession first smooth then forward;
            exhibit state lifecycle : Common::Lifecycle;
        }
        requirement controllerMass_0475 : Common::MassLimit {
            subject component : Controller_0475;
            attribute :>> limit = 2.0 [kg];
        }
    }

    package Subsystem_0476 {
        part def Sensor_0476 :> Common::Component {
            attribute :>> mass = 0.21 [kg];
            attribute :>> cost = 46.0;
            attribute range : Real = 126.0;
            port data : Common::DataPort;
        }
        part def Controller_0476 :> Common::Component {
            attribute :>> mass = 1.00 [kg];
            attribute :>> cost = 276.0;
            port supply : Common::PowerPort;
            part sensors : Sensor_0476[2];
            action smooth : Common::Process;
            action forward : Common::Process;
            succession first smooth then forward;
            exhibit state lifecycle : Common::Lifecycle;
        }
        requirement controllerMass_0476 : Common::MassLimit {
            subject component : Controller_0476;
            attribute :>> limit = 2.0 [kg];
        }
    }

    package Subsystem_0477 {
        part def Sensor_0477 :> Common::Component {
            attribute :>> mass = 0.22 [kg];
            attribute :>> cost = 47.0;
            attribute range : Real = 127.0;
            port data : Common::DataPort;
        }
        part def Controller_0477 :> Common::Component {
            attribute :>> mass = 1.10 [kg];
            attribute :>> cost = 277.0;
            port supply : Common::PowerPort;
            part sensors : Sensor_0477[2];
            action smooth : Common::Process;
            action forward : Common::Process;
            succession first smooth then forward;
            exhibit state lifecycle : Common::Lifecycle;
        }
        requirement controllerMass_0477 : Common::MassLimit {
            subject component : Controller_0477;
            attribute :>> limit = 2.0 [kg];
        }
    }

    package Subsystem_0478 {
        part def Sensor_0478 :> Common::Component {
            attribute :>> mass = 0.23 [kg];
            attribute :>> cost = 48.0;
            attribute range : Real = 128.0;
            port data : Common::DataPort;
        }
        part def Controller_0478 :> Common::Component {
            attribute :>> mass = 1.20 [kg];
            attribute :>> cost = 278.0;
            port supply : Common::PowerPort;
            part sensors : Sensor_0478[2];
            action smooth : Common::Process;
            action forward : Common::Process;
            succession first smooth then forward;
            exhibit state lifecycle : Common::Lifecycle;
        }
        requirement controllerMass_0478 : Common::MassLimit {
            subject component : Controller_0478;
            attribute :>> limit = 2.0 [kg];
        }
    }

    package Subsystem_0479 {
        part def Sensor_0479 :> Common::Component {
            attribute :>> mass = 0.24 [kg];
            attribute :>> cost = 49.0;
            attribute range : Real = 129.0;
            port data : Common::DataPort;
        }
        part def Controller_0479 :> Common::Component {
            attribute :>> mass = 1.30 [kg];
            attribute :>> cost = 279.0;
            port supply : Common::PowerPort;
            part sensors : Sensor_0479[2];
            action smooth : Common::Process;
            action forward : Common::Process;
            succession first smooth then forward;
            exhibit state lifecycle : Common::Lifecycle;
        }
        requirement controllerMass_0479 : Common::MassLimit {
            subject component : Controller_0479;
            attribute :>> limit = 2.0 [kg];
        }
    }

    package Subsystem_0480 {
        part def Sensor_0480 :> Common::Component {
            attribute :>> mass = 0.20 [kg];
            attribute :>> cost = 30.0;
            attribute range : Real = 130.0;
            port data : Common::DataPort;
        }
        part def Controller_0480 :> Common::Component {
            attribute :>> mass = 1.40 [kg];
            attribute :>> cost = 280.0;
            port supply : Common::PowerPort;
            part sensors : Sensor_0480[2];
            action smooth : Common::Process;
            action forward : Common::Process;
            succession first smooth then forward;
            exhibit state lifecycle : Common::Lifecycle;
        }
        requirement controllerMass_0480 : Common::MassLimit {
            subject component : Controller_0480;
            attribute :>> limit = 2.0 [kg];
        }
    }

    package Subsystem_0481 {
        part def Sensor_0481 :> Common::Component {
            attribute :>> mass = 0.21 [kg];
            attribute :>> cost = 31.0;
            attribute range : Real = 131.0;
            port data : Common::DataPort;
        }
        part def Controller_0481 :> Common::Component {
            attribute :>> mass = 1.50 [kg];
            attribute :>> cost = 281.0;
            port supply : Common::PowerPort;
            part sensors : Sensor_0481[2];
            action smooth : Common::Process;
            action forward : Common::Process;
            succession first smooth then forward;
            exhibit state lifecycle : Common::Lifecycle;
        }
        requirement controllerMass_0481 : Common::MassLimit {
            subject component : Controller_0481;
            attribute :>> limit = 2.0 [kg];
        }
    }

    package Subsystem_0482 {
        part def Sensor_0482 :> Common::Component {
            attribute :>> mass = 0.22 [kg];
            attribute :>> cost = 32.0;
            attribute range : Real = 132.0;
            port data : Common::DataPort;
        }
        part def Controller_0482 :> Common::Component {
            attribute :>> mass = 1.60 [kg];
            attribute :>> cost = 282.0;
            port supply : Common::PowerPort;
            part sensors : Sensor_0482[2];
            action smooth : Common::Process;
            action forward : Common::Process;
            succession first smooth then forward;
            exhibit state lifecycle : Common::Lifecycle;
        }
        requirement controllerMass_0482 : Common::MassLimit {
            subject component : Controller_0482;
            attribute :>> limit = 2.0 [kg];
        }
    }

    package Subsystem_0483 {
        part def Sensor_0483 :> Common::Component {
            attribute :>> mass = 0.23 [kg];
            attribute :>> cost = 33.0;
            attribute range : Real = 133.0;
            port data : Common::DataPort;
        }
        part def Controller_0483 :> Common::Component {
            attribute :>> mass = 1.00 [kg];
            attribute :>> cost = 283.0;
            port supply : Common::PowerPort;
            part sensors : Sensor_0483[2];
            action smooth : Common::Process;
            action forward : Common::Process;
            succession first smooth then forward;
            exhibit state lifecycle : Common::Lifecycle;
        }
        requirement controllerMass_0483 : Common::MassLimit {
            subject component : Controller_0483;
            attribute :>> limit = 2.0 [kg];
        }
    }

    package Subsystem_0484 {
        part def Sensor_0484 :> Common::Component {
            attribute :>> mass = 0.24 [kg];
            attribute :>> cost = 34.0;
            attribute range : Real = 134.0;
            port data : Common::DataPort;
        }
        part def Controller_0484 :> Common::Component {
            attribute :>> mass = 1.10 [kg];
            attribute :>> cost = 284.0;
            port supply : Common::PowerPort;
            part sensors : Sensor_0484[2];
            action smooth : Common::Process;
            action forward : Common::Process;
            succession first smooth then forward;
            exhibit state lifecycle : Common::Lifecycle;
        }
        requirement controllerMass_0484 : Common::MassLimit {
            subject component : Controller_0484;
            attribute :>> limit = 2.0 [kg];
        }
    }

    package Subsystem_0485 {
        part def Sensor_0485 :> Common::Component {
            attribute :>> mass = 0.20 [kg];
            attribute :>> cost = 35.0;
            attribute range : Real = 135.0;
            port data : Common::DataPort;
        }
        part def Controller_0485 :> Common::Component {
            attribute :>> mass = 1.20 [kg];
            attribute :>> cost = 285.0;
            port supply : Common::PowerPort;
            part sensors : Sensor_0485[2];
            action smooth : Common::Process;
            action forward : Common::Process;
            succession first smooth then forward;
            exhibit state lifecycle : Common::Lifecycle;
        }
        requirement controllerMass_0485 : Common::MassLimit {
            subject component : Controller_0485;
            attribute :>> limit = 2.0 [kg];
        }
    }

    package Subsystem_0486 {
        part def Sensor_0486 :> Common::Component {
            attribute :>> mass = 0.21 [kg];
            attribute :>> cost = 36.0;
            attribute range : Real = 136.0;
            port data : Common::DataPort;
        }
        part def Controller_0486 :> Common::Component {
            attribute :>> mass = 1.30 [kg];
            attribute :>> cost = 286.0;
            port supply : Common::PowerPort;
            part sensors : Sensor_0486[2];
            action smooth : Common::Process;
            action forward : Common::Process;
            succession first smooth then forward;
            exhibit state lifecycle : Common::Lifecycle;
        }
        requirement controllerMass_0486 : Common::MassLimit {
            subject component : Controller_0486;
            attribute :>> limit = 2.0 [kg];
        }
    }

    package Subsystem_0487 {
        part def Sensor_0487 :> Common::Component {
            attribute :>> mass = 0.22 [kg];
            attribute :>> cost = 37.0;
            attribute range : Real = 137.0;
            port data : Common::DataPort;
        }
        part def Controller_0487 :> Common::Component {
            attribute :>> mass = 1.40 [kg];
            attribute :>> cost = 287.0;
            port supply : Common::PowerPort;
            part sensors : Sensor_0487[2];
            action smooth : Common::Process;
            action forward : Common::Process;
            succession first smooth then forward;
            exhibit state lifecycle : Common::Lifecycle;
        }
        requirement controllerMass_0487 : Common::MassLimit {
            subject component : Controller_0487;
            attribute :>> limit = 2.0 [kg];
        }
    }

    package Subsystem_0488 {
        part def Sensor_0488 :> Common::Component {
            attribute :>> mass = 0.23 [kg];
            attribute :>> cost = 38.0;
            attribute range : Real = 138.0;
            port data : Common::DataPort;
        }
        part def Controller_0488 :> Common::Component {
            attribute :>> mass = 1.50 [kg];
            attribute :>> cost = 288.0;
            port supply : Common::PowerPort;
            part sensors : Sensor_0488[2];
            action smooth : Common::Process;
            action forward : Common::Process;
            succession first smooth then forward;
            exhibit state lifecycle : Common::Lifecycle;
        }
        requirement controllerMass_0488 : Common::MassLimit {
            subject component : Controller_0488;
            attribute :>> limit = 2.0 [kg];
        }
    }

    package Subsystem_0489 {
        part def Sensor_0489 :> Common::Component {
            attribute :>> mass = 0.24 [kg];
            attribute :>> cost = 39.0;
            attribute range : Real = 139.0;
            port data : Common::DataPort;
        }
        part def Controller_0489 :> Common::Component {
            attribute :>> mass = 1.60 [kg];
            attribute :>> cost = 289.0;
            port supply : Common::PowerPort;
            part sensors : Sensor_0489[2];
            action smooth : Common::Process;
            action forward : Common::Process;
            succession first smooth then forward;
            exhibit state lifecycle : Common::Lifecycle;
        }
        requirement controllerMass_0489 : Common::MassLimit {
            subject component : Controller_0489;
            attribute :>> limit = 2.0 [kg];
        }
    }

    package Subsystem_0490 {
        part def Sensor_0490 :> Common::Component {
            attribute :>> mass = 0.20 [kg];
            attribute :>> cost = 40.0;
            attribute range : Real = 140.0;
            port data : Common::DataPort;
        }
        part def Controller_0490 :> Common::Component {
            attribute :>> mass = 1.00 [kg];
            attribute :>> cost = 290.0;
            port supply : Common::PowerPort;
            part sensors : Sensor_0490[2];
            action smooth : Common::Process;
            action forward : Common::Process;
            succession first smooth then forward;
            exhibit state lifecycle : Common::Lifecycle;
        }
        requirement controllerMass_0490 : Common::MassLimit {
            subject component : Controller_0490;
            attribute :>> limit = 2.0 [kg];
        }
    }

    package Subsystem_0491 {
        part def Sensor_0491 :> Common::Component {
            attribute :>> mass = 0.21 [kg];
            attribute :>> cost = 41.0;
            attribute range : Real = 141.0;
            port data : Common::DataPort;
        }
        part def Controller_0491 :> Common::Component {
            attribute :>> mass = 1.10 [kg];
            attribute :>> cost = 291.0;
            port supply : Common::PowerPort;
            part sensors : Sensor_0491[2];
            action smooth : Common::Process;
            action forward : Common::Process;
            succession first smooth then forward;
            exhibit state lifecycle : Common::Lifecycle;
        }
        requirement controllerMass_0491 : Common::MassLimit {
            subject component : Controller_0491;
            attribute :>> limit = 2.0 [kg];
        }
    }

    package Subsystem_0492 {
        part def Sensor_0492 :> Common::Component {
            attribute :>> mass = 0.22 [kg];
            attribute :>> cost = 42.0;
            attribute range : Real = 142.0;
            port data : Common::DataPort;
        }
        part def Controller_0492 :> Common::Component {
            attribute :>> mass = 1.20 [kg];
            attribute :>> cost = 292.0;
            port supply : Common::PowerPort;
            part sensors : Sensor_0492[2];
            action smooth : Common::Process;
            action forward : Common::Process;
            succession first smooth then forward;
            exhibit state lifecycle : Common::Lifecycle;
        }
        requirement controllerMass_0492 : Common::MassLimit {
            subject component : Controller_0492;
            attribute :>> limit = 2.0 [kg];
        }
    }

    package Subsystem_0493 {
        part def Sensor_0493 :> Common::Component {
            attribute :>> mass = 0.23 [kg];
            attribute :>> cost = 43.0;
            attribute range : Real = 143.0;
            port data : Common::DataPort;
        }
        part def Controller_0493 :> Common::Component {
            attribute :>> mass = 1.30 [kg];
            attribute :>> cost = 293.0;
            port supply : Common::PowerPort;
            part sensors : Sensor_0493[2];
            action smooth : Common::Process;
            action forward : Common::Process;
            succession first smooth then forward;
            exhibit state lifecycle : Common::Lifecycle;
        }
        requirement controllerMass_0493 : Common::MassLimit {
            subject component : Controller_0493;
            attribute :>> limit = 2.0 [kg];
        }
    }

    package Subsystem_0494 {
        part def Sensor_0494 :> Common::Component {
            attribute :>> mass = 0.24 [kg];
            attribute :>> cost = 44.0;
            attribute range : Real = 144.0;
            port data : Common::DataPort;
        }
        part def Controller_0494 :> Common::Component {
            attribute :>> mass = 1.40 [kg];
            attribute :>> cost = 294.0;
            port supply : Common::PowerPort;
            part sensors : Sensor_0494[2];
            action smooth : Common::Process;
            action forward : Common::Process;
            succession first smooth then forward;
            exhibit state lifecycle : Common::Lifecycle;
        }
        requirement controllerMass_0494 : Common::MassLimit {
            subject component : Controller_0494;
            attribute :>> limit = 2.0 [kg];
        }
    }

    package Subsystem_0495 {
        part def Sensor_0495 :> Common::Component {
            attribute :>> mass = 0.20 [kg];
            attribute :>> cost = 45.0;
            attribute range : Real = 145.0;
            port data : Common::DataPort;
        }
        part def Controller_0495 :> Common::Component {
            attribute :>> mass = 1.50 [kg];
            attribute :>> cost = 295.0;
            port supply : Common::PowerPort;
            part sensors : Sensor_0495[2];
            action smooth : Common::Process;
            action forward : Common::Process;
            succession first smooth then forward;
            exhibit state lifecycle : Common::Lifecycle;
        }
        requirement controllerMass_0495 : Common::MassLimit {
            subject component : Controller_0495;
            attribute :>> limit = 2.0 [kg];
        }
    }

    package Subsystem_0496 {
        part def Sensor_0496 :> Common::Component {
            attribute :>> mass = 0.21 [kg];
            attribute :>> cost = 46.0;
            attribute range : Real = 146.0;
            port data : Common::DataPort;
        }
        part def Controller_0496 :> Common::Component {
            attribute :>> mass = 1.60 [kg];
            attribute :>> cost = 296.0;
            port supply : Common::PowerPort;
            part sensors : Sensor_0496[2];
            action smooth : Common::Process;
            action forward : Common::Process;
            succession first smooth then forward;
            exhibit state lifecycle : Common::Lifecycle;
        }
        requirement controllerMass_0496 : Common::MassLimit {
            subject component : Controller_0496;
            attribute :>> limit = 2.0 [kg];
        }
    }

    package Subsystem_0497 {
        part def Sensor_0497 :> Common::Component {
            attribute :>> mass = 0.22 [kg];
            attribute :>> cost = 47.0;
            attribute range : Real = 147.0;
            port data : Common::DataPort;
        }
        part def Controller_0497 :> Common::Component {
            attribute :>> mass = 1.00 [kg];
            attribute :>> cost = 297.0;
            port supply : Common::PowerPort;
            part sensors : Sensor_0497[2];
            action smooth : Common::Process;
            action forward : Common::Process;
            succession first smooth then forward;
            exhibit state lifecycle : Common::Lifecycle;
        }
        requirement controllerMass_0497 : Common::MassLimit {
            subject component : Controller_0497;
            attribute :>> limit = 2.0 [kg];
        }
    }

    package Subsystem_0498 {
        part def Sensor_0498 :> Common::Component {
            attribute :>> mass = 0.23 [kg];
            attribute :>> cost = 48.0;
            attribute range : Real = 148.0;
            port data : Common::DataPort;
        }
        part def Controller_0498 :> Common::Component {
            attribute :>> mass = 1.10 [kg];
            attribute :>> cost = 298.0;
            port supply : Common::PowerPort;
            part sensors : Sensor_0498[2];
            action smooth : Common::Process;
            action forward : Common::Process;
            succession first smooth then forward;
            exhibit state lifecycle : Common::Lifecycle;
        }
        requirement controllerMass_0498 : Common::MassLimit {
            subject component : Controller_0498;
            attribute :>> limit = 2.0 [kg];
        }
    }

    package Subsystem_0499 {
        part def Sensor_0499 :> Common::Component {
            attribute :>> mass = 0.24 [kg];
            attribute :>> cost = 49.0;
            attribute range : Real = 149.0;
            port data : Common::DataPort;
        }
        part def Controller_0499 :> Common::Component {
            attribute :>> mass = 1.20 [kg];
            attribute :>> cost = 299.0;
            port supply : Common::PowerPort;
            part sensors : Sensor_0499[2];
            action smooth : Common::Process;
            action forward : Common::Process;
            succession first smooth then forward;
            exhibit state lifecycle : Common::Lifecycle;
        }
        requirement controllerMass_0499 : Common::MassLimit {
            subject component : Controller_0499;
            attribute :>> limit = 2.0 [kg];
        }
    }

    package Subsystem_0500 {
        part def Sensor_0500 :> Common::Component {
            attribute :>> mass = 0.20 [kg];
            attribute :>> cost = 30.0;
            attribute range : Real = 100.0;
            port data : Common::DataPort;
        }
        part def Controller_0500 :> Common::Component {
            attribute :>> mass = 1.30 [kg];
            attribute :>> cost = 200.0;
            port supply : Common::PowerPort;
            part sensors : Sensor_0500[2];
            action smooth : Common::Process;
            action forward : Common::Process;
            succession first smooth then forward;
            exhibit state lifecycle : Common::Lifecycle;
        }
        requirement controllerMass_0500 : Common::MassLimit {
            subject component : Controller_0500;
            attribute :>> limit = 2.0 [kg];
        }
    }

    package Subsystem_0501 {
        part def Sensor_0501 :> Common::Component {
            attribute :>> mass = 0.21 [kg];
            attribute :>> cost = 31.0;
            attribute range : Real = 101.0;
            port data : Common::DataPort;
        }
        part def Controller_0501 :> Common::Component {
            attribute :>> mass = 1.40 [kg];
            attribute :>> cost = 201.0;
            port supply : Common::PowerPort;
            part sensors : Sensor_0501[2];
            action smooth : Common::Process;
            action forward : Common::Process;
            succession first smooth then forward;
            exhibit state lifecycle : Common::Lifecycle;
        }
        requirement controllerMass_0501 : Common::MassLimit {
            subject component : Controller_0501;
            attribute :>> limit = 2.0 [kg];
        }
    }

    package Subsystem_0502 {
        part def Sensor_0502 :> Common::Component {
            attribute :>> mass = 0.22 [kg];
            attribute :>> cost = 32.0;
            attribute range : Real = 102.0;
            port data : Common::DataPort;
        }
        part def Controller_0502 :> Common::Component {
            attribute :>> mass = 1.50 [kg];
            attribute :>> cost = 202.0;
            port supply : Common::PowerPort;
            part sensors : Sensor_0502[2];
            action smooth : Common::Process;
            action forward : Common::Process;
            succession first smooth then forward;
            exhibit state lifecycle : Common::Lifecycle;
        }
        requirement controllerMass_0502 : Common::MassLimit {
            subject component : Controller_0502;
            attribute :>> limit = 2.0 [kg];
        }
    }

    package Subsystem_0503 {
        part def Sensor_0503 :> Common::Component {
            attribute :>> mass = 0.23 [kg];
            attribute :>> cost = 33.0;
            attribute range : Real = 103.0;
            port data : Common::DataPort;
        }
        part def Controller_0503 :> Common::Component {
            attribute :>> mass = 1.60 [kg];
            attribute :>> cost = 203.0;
            port supply : Common::PowerPort;
            part sensors : Sensor_0503[2];
            action smooth : Common::Process;
            action forward : Common::Process;
            succession first smooth then forward;
            exhibit state lifecycle : Common::Lifecycle;
        }
        requirement controllerMass_0503 : Common::MassLimit {
            subject component : Controller_0503;
            attribute :>> limit = 2.0 [kg];
        }
    }

    package Subsystem_0504 {
        part def Sensor_0504 :> Common::Component {
            attribute :>> mass = 0.24 [kg];
            attribute :>> cost = 34.0;
            attribute range : Real = 104.0;
            port data : Common::DataPort;
        }
        part def Controller_0504 :> Common::Component {
            attribute :>> mass = 1.00 [kg];
            attribute :>> cost = 204.0;
            port supply : Common::PowerPort;
            part sensors : Sensor_0504[2];
            action smooth : Common::Process;
            action forward : Common::Process;
            succession first smooth then forward;
            exhibit state lifecycle : Common::Lifecycle;
        }
        requirement controllerMass_0504 : Common::MassLimit {
            subject component : Controller_0504;
            attribute :>> limit = 2.0 [kg];
        }
    }

    package Subsystem_0505 {
        part def Sensor_0505 :> Common::Component {
            attribute :>> mass = 0.20 [kg];
            attribute :>> cost = 35.0;
            attribute range : Real = 105.0;
            port data : Common::DataPort;
        }
        part def Controller_0505 :> Common::Component {
            attribute :>> mass = 1.10 [kg];
            attribute :>> cost = 205.0;
            port supply : Common::PowerPort;
            part sensors : Sensor_0505[2];
            action smooth : Common::Process;
            action forward : Common::Process;
            succession first smooth then forward;
            exhibit state lifecycle : Common::Lifecycle;
        }
        requirement controllerMass_0505 : Common::MassLimit {
            subject component : Controller_0505;
            attribute :>> limit = 2.0 [kg];
        }
    }

    package Subsystem_0506 {
        part def Sensor_0506 :> Common::Component {
            attribute :>> mass = 0.21 [kg];
            attribute :>> cost = 36.0;
            attribute range : Real = 106.0;
            port data : Common::DataPort;
        }
        part def Controller_0506 :> Common::Component {
            attribute :>> mass = 1.20 [kg];
            attribute :>> cost = 206.0;
            port supply : Common::PowerPort;
            part sensors : Sensor_0506[2];
            action smooth : Common::Process;
            action forward : Common::Process;
            succession first smooth then forward;
            exhibit state lifecycle : Common::Lifecycle;
        }
        requirement controllerMass_0506 : Common::MassLimit {
            subject component : Controller_0506;
            attribute :>> limit = 2.0 [kg];
        }
    }

    package Subsystem_0507 {
        part def Sensor_0507 :> Common::Component {
            attribute :>> mass = 0.22 [kg];
            attribute :>> cost = 37.0;
            attribute range : Real = 107.0;
            port data : Common::DataPort;
        }
        part def Controller_0507 :> Common::Component {
            attribute :>> mass = 1.30 [kg];
            attribute :>> cost = 207.0;
            port supply : Common::PowerPort;
            part sensors : Sensor_0507[2];
            action smooth : Common::Process;
            action forward : Common::Process;
            succession first smooth then forward;
            exhibit state lifecycle : Common::Lifecycle;
        }
        requirement controllerMass_0507 : Common::MassLimit {
            subject component : Controller_0507;
            attribute :>> limit = 2.0 [kg];
        }
    }

    package Subsystem_0508 {
        part def Sensor_0508 :> Common::Component {
            attribute :>> mass = 0.23 [kg];
            attribute :>> cost = 38.0;
            attribute range : Real = 108.0;
            port data : Common::DataPort;
        }
        part def Controller_0508 :> Common::Component {
            attribute :>> mass = 1.40 [kg];
            attribute :>> cost = 208.0;
            port supply : Common::PowerPort;
            part sensors : Sensor_0508[2];
            action smooth : Common::Process;
            action forward : Common::Process;
            succession first smooth then forward;
            exhibit state lifecycle : Common::Lifecycle;
        }
        requirement controllerMass_0508 : Common::MassLimit {
            subject component : Controller_0508;
            attribute :>> limit = 2.0 [kg];
        }
    }

    package Subsystem_0509 {
        part def Sensor_0509 :> Common::Component {
            attribute :>> mass = 0.24 [kg];
            attribute :>> cost = 39.0;
            attribute range : Real = 109.0;
            port data : Common::DataPort;
        }
        part def Controller_0509 :> Common::Component {
            attribute :>> mass = 1.50 [kg];
            attribute :>> cost = 209.0;
            port supply : Common::PowerPort;
            part sensors : Sensor_0509[2];
            action smooth : Common::Process;
            action forward : Common::Process;
            succession first smooth then forward;
            exhibit state lifecycle : Common::Lifecycle;
        }
        requirement controllerMass_0509 : Common::MassLimit {
            subject component : Controller_0509;
            attribute :>> limit = 2.0 [kg];
        }
    }

    package Subsystem_0510 {
        part def Sensor_0510 :> Common::Component {
            attribute :>> mass = 0.20 [kg];
            attribute :>> cost = 40.0;
            attribute range : Real = 110.0;
            port data : Common::DataPort;
        }
        part def Controller_0510 :> Common::Component {
            attribute :>> mass = 1.60 [kg];
            attribute :>> cost = 210.0;
            port supply : Common::PowerPort;
            part sensors : Sensor_0510[2];
            action smooth : Common::Process;
            action forward : Common::Process;
            succession first smooth then forward;
            exhibit state lifecycle : Common::Lifecycle;
        }
        requirement controllerMass_0510 : Common::MassLimit {
            subject component : Controller_0510;
            attribute :>> limit = 2.0 [kg];
        }
    }

    package Subsystem_0511 {
        part def Sensor_0511 :> Common::Component {
            attribute :>> mass = 0.21 [kg];
            attribute :>> cost = 41.0;
            attribute range : Real = 111.0;
            port data : Common::DataPort;
        }
        part def Controller_0511 :> Common::Component {
            attribute :>> mass = 1.00 [kg];
            attribute :>> cost = 211.0;
            port supply : Common::PowerPort;
            part sensors : Sensor_0511[2];
            action smooth : Common::Process;
            action forward : Common::Process;
            succession first smooth then forward;
            exhibit state lifecycle : Common::Lifecycle;
        }
        requirement controllerMass_0511 : Common::MassLimit {
            subject component : Controller_0511;
            attribute :>> limit = 2.0 [kg];
        }
    }

    package Subsystem_0512 {
        part def Sensor_0512 :> Common::Component {
            attribute :>> mass = 0.22 [kg];
            attribute :>> cost = 42.0;
            attribute range : Real = 112.0;
            port data : Common::DataPort;
        }
        part def Controller_0512 :> Common::Component {
            attribute :>> mass = 1.10 [kg];
            attribute :>> cost = 212.0;
            port supply : Common::PowerPort;
            part sensors : Sensor_0512[2];
            action smooth : Common::Process;
            action forward : Common::Process;
            succession first smooth then forward;
            exhibit state lifecycle : Common::Lifecycle;
        }
        requirement controllerMass_0512 : Common::MassLimit {
            subject component : Controller_0512;
            attribute :>> limit = 2.0 [kg];
        }
    }

    package Subsystem_0513 {
        part def Sensor_0513 :> Common::Component {
            attribute :>> mass = 0.23 [kg];
            attribute :>> cost = 43.0;
            attribute range : Real = 113.0;
            port data : Common::DataPort;
        }
        part def Controller_0513 :> Common::Component {
            attribute :>> mass = 1.20 [kg];
            attribute :>> cost = 213.0;
            port supply : Common::PowerPort;
            part sensors : Sensor_0513[2];
            action smooth : Common::Process;
            action forward : Common::Process;
            succession first smooth then forward;
            exhibit state lifecycle : Common::Lifecycle;
        }
        requirement controllerMass_0513 : Common::MassLimit {
            subject component : Controller_0513;
            attribute :>> limit = 2.0 [kg];
        }
    }

    package Subsystem_0514 {
        part def Sensor_0514 :> Common::Component {
            attribute :>> mass = 0.24 [kg];
            attribute :>> cost = 44.0;
            attribute range : Real = 114.0;
            port data : Common::DataPort;
        }
        part def Controller_0514 :> Common::Component {
            attribute :>> mass = 1.30 [kg];
            attribute :>> cost = 214.0;
            port supply : Common::PowerPort;
            part sensors : Sensor_0514[2];
            action smooth : Common::Process;
            action forward : Common::Process;
            succession first smooth then forward;
            exhibit state lifecycle : Common::Lifecycle;
        }
        requirement controllerMass_0514 : Common::MassLimit {
            subject component : Controller_0514;
            attribute :>> limit = 2.0 [kg];
        }
    }

    package Subsystem_0515 {
        part def Sensor_0515 :> Common::Component {
            attribute :>> mass = 0.20 [kg];
            attribute :>> cost = 45.0;
            attribute range : Real = 115.0;
            port data : Common::DataPort;
        }
        part def Controller_0515 :> Common::Component {
            attribute :>> mass = 1.40 [kg];
            attribute :>> cost = 215.0;
            port supply : Common::PowerPort;
            part sensors : Sensor_0515[2];
            action smooth : Common::Process;
            action forward : Common::Process;
            succession first smooth then forward;
            exhibit state lifecycle : Common::Lifecycle;
        }
        requirement controllerMass_0515 : Common::MassLimit {
            subject component : Controller_0515;
            attribute :>> limit = 2.0 [kg];
        }
    }

    package Subsystem_0516 {
        part def Sensor_0516 :> Common::Component {
            attribute :>> mass = 0.21 [kg];
            attribute :>> cost = 46.0;
            attribute range : Real = 116.0;
            port data : Common::DataPort;
        }
        part def Controller_0516 :> Common::Component {
            attribute :>> mass = 1.50 [kg];
            attribute :>> cost = 216.0;
            port supply : Common::PowerPort;
            part sensors : Sensor_0516[2];
            action smooth : Common::Process;
            action forward : Common::Process;
            succession first smooth then forward;
            exhibit state lifecycle : Common::Lifecycle;
        }
        requirement controllerMass_0516 : Common::MassLimit {
            subject component : Controller_0516;
            attribute :>> limit = 2.0 [kg];
        }
    }

    package Subsystem_0517 {
        part def Sensor_0517 :> Common::Component {
            attribute :>> mass = 0.22 [kg];
            attribute :>> cost = 47.0;
            attribute range : Real = 117.0;
            port data : Common::DataPort;
        }
        part def Controller_0517 :> Common::Component {
            attribute :>> mass = 1.60 [kg];
            attribute :>> cost = 217.0;
            port supply : Common::PowerPort;
            part sensors : Sensor_0517[2];
            action smooth : Common::Process;
            action forward : Common::Process;
            succession first smooth then forward;
            exhibit state lifecycle : Common::Lifecycle;
        }
        requirement controllerMass_0517 : Common::MassLimit {
            subject component : Controller_0517;
            attribute :>> limit = 2.0 [kg];
        }
    }

    package Subsystem_0518 {
        part def Sensor_0518 :> Common::Component {
            attribute :>> mass = 0.23 [kg];
            attribute :>> cost = 48.0;
            attribute range : Real = 118.0;
            port data : Common::DataPort;
        }
        part def Controller_0518 :> Common::Component {
            attribute :>> mass = 1.00 [kg];
            attribute :>> cost = 218.0;
            port supply : Common::PowerPort;
            part sensors : Sensor_0518[2];
            action smooth : Common::Process;
            action forward : Common::Process;
            succession first smooth then forward;
            exhibit state lifecycle : Common::Lifecycle;
        }
        requirement controllerMass_0518 : Common::MassLimit {
            subject component : Controller_0518;
            attribute :>> limit = 2.0 [kg];
        }
    }

    package Subsystem_0519 {
        part def Sensor_0519 :> Common::Component {
            attribute :>> mass = 0.24 [kg];
            attribute :>> cost = 49.0;
            attribute range : Real = 119.0;
            port data : Common::DataPort;
        }
        part def Controller_0519 :> Common::Component {
            attribute :>> mass = 1.10 [kg];
            attribute :>> cost = 219.0;
            port supply : Common::PowerPort;
            part sensors : Sensor_0519[2];
            action smooth : Common::Process;
            action forward : Common::Process;
            succession first smooth then forward;
            exhibit state lifecycle : Common::Lifecycle;
        }
        requirement controllerMass_0519 : Common::MassLimit {
            subject component : Controller_0519;
            attribute :>> limit = 2.0 [kg];
        }
    }

    package Subsystem_0520 {
        part def Sensor_0520 :> Common::Component {
            attribute :>> mass = 0.20 [kg];
            attribute :>> cost = 30.0;
            attribute range : Real = 120.0;
            port data : Common::DataPort;
        }
        part def Controller_0520 :> Common::Component {
            attribute :>> mass = 1.20 [kg];
            attribute :>> cost = 220.0;
            port supply : Common::PowerPort;
            part sensors : Sensor_0520[2];
            action smooth : Common::Process;
            action forward : Common::Process;
            succession first smooth then forward;
            exhibit state lifecycle : Common::Lifecycle;
        }
        requirement controllerMass_0520 : Common::MassLimit {
            subject component : Controller_0520;
            attribute :>> limit = 2.0 [kg];
        }
    }

    package Subsystem_0521 {
        part def Sensor_0521 :> Common::Component {
            attribute :>> mass = 0.21 [kg];
            attribute :>> cost = 31.0;
            attribute range : Real = 121.0;
            port data : Common::DataPort;
        }
        part def Controller_0521 :> Common::Component {
            attribute :>> mass = 1.30 [kg];
            attribute :>> cost = 221.0;
            port supply : Common::PowerPort;
            part sensors : Sensor_0521[2];
            action smooth : Common::Process;
            action forward : Common::Process;
            succession first smooth then forward;
            exhibit state lifecycle : Common::Lifecycle;
        }
        requirement controllerMass_0521 : Common::MassLimit {
            subject component : Controller_0521;
            attribute :>> limit = 2.0 [kg];
        }
    }

    package Subsystem_0522 {
        part def Sensor_0522 :> Common::Component {
            attribute :>> mass = 0.22 [kg];
            attribute :>> cost = 32.0;
            attribute range : Real = 122.0;
            port data : Common::DataPort;
        }
        part def Controller_0522 :> Common::Component {
            attribute :>> mass = 1.40 [kg];
            attribute :>> cost = 222.0;
            port supply : Common::PowerPort;
            part sensors : Sensor_0522[2];
            action smooth : Common::Process;
            action forward : Common::Process;
            succession first smooth then forward;
            exhibit state lifecycle : Common::Lifecycle;
        }
        requirement controllerMass_0522 : Common::MassLimit {
            subject component : Controller_0522;
            attribute :>> limit = 2.0 [kg];
        }
    }

    package Subsystem_0523 {
        part def Sensor_0523 :> Common::Component {
            attribute :>> mass = 0.23 [kg];
            attribute :>> cost = 33.0;
            attribute range : Real = 123.0;
            port data : Common::DataPort;
        }
        part def Controller_0523 :> Common::Component {
            attribute :>> mass = 1.50 [kg];
            attribute :>> cost = 223.0;
            port supply : Common::PowerPort;
            part sensors : Sensor_0523[2];
            action smooth : Common::Process;
            action forward : Common::Process;
            succession first smooth then forward;
            exhibit state lifecycle : Common::Lifecycle;
        }
        requirement controllerMass_0523 : Common::MassLimit {
            subject component : Controller_0523;
            attribute :>> limit = 2.0 [kg];
        }
    }

    package Subsystem_0524 {
        part def Sensor_0524 :> Common::Component {
            attribute :>> mass = 0.24 [kg];
            attribute :>> cost = 34.0;
            attribute range : Real = 124.0;
            port data : Common::DataPort;
        }
        part def Controller_0524 :> Common::Component {
            attribute :>> mass = 1.60 [kg];
            attribute :>> cost = 224.0;
            port supply : Common::PowerPort;
            part sensors : Sensor_0524[2];
            action smooth : Common::Process;
            action forward : Common::Process;
            succession first smooth then forward;
            exhibit state lifecycle : Common::Lifecycle;
        }
        requirement controllerMass_0524 : Common::MassLimit {
            subject component : Controller_0524;
            attribute :>> limit = 2.0 [kg];
        }
    }

    package Subsystem_0525 {
        part def Sensor_0525 :> Common::Component {
            attribute :>> mass = 0.20 [kg];
            attribute :>> cost = 35.0;
            attribute range : Real = 125.0;
            port data : Common::DataPort;
        }
        part def Controller_0525 :> Common::Component {
            attribute :>> mass = 1.00 [kg];
            attribute :>> cost = 225.0;
            port supply : Common::PowerPort;
            part sensors : Sensor_0525[2];
            action smooth : Common::Process;
            action forward : Common::Process;
            succession first smooth then forward;
            exhibit state lifecycle : Common::Lifecycle;
        }
        requirement controllerMass_0525 : Common::MassLimit {
            subject component : Controller_0525;
            attribute :>> limit = 2.0 [kg];
        }
    }

    package Subsystem_0526 {
        part def Sensor_0526 :> Common::Component {
            attribute :>> mass = 0.21 [kg];
            attribute :>> cost = 36.0;
            attribute range : Real = 126.0;
            port data : Common::DataPort;
        }
        part def Controller_0526 :> Common::Component {
            attribute :>> mass = 1.10 [kg];
            attribute :>> cost = 226.0;
            port supply : Common::PowerPort;
            part sensors : Sensor_0526[2];
            action smooth : Common::Process;
            action forward : Common::Process;
            succession first smooth then forward;
            exhibit state lifecycle : Common::Lifecycle;
        }
        requirement controllerMass_0526 : Common::MassLimit {
            subject component : Controller_0526;
            attribute :>> limit = 2.0 [kg];
        }
    }

    package Subsystem_0527 {
        part def Sensor_0527 :> Common::Component {
            attribute :>> mass = 0.22 [kg];
            attribute :>> cost = 37.0;
            attribute range : Real = 127.0;
            port data : Common::DataPort;
        }
        part def Controller_0527 :> Common::Component {
            attribute :>> mass = 1.20 [kg];
            attribute :>> cost = 227.0;
            port supply : Common::PowerPort;
            part sensors : Sensor_0527[2];
            action smooth : Common::Process;
            action forward : Common::Process;
            succession first smooth then forward;
            exhibit state lifecycle : Common::Lifecycle;
        }
        requirement controllerMass_0527 : Common::MassLimit {
            subject component : Controller_0527;
            attribute :>> limit = 2.0 [kg];
        }
    }

    package Subsystem_0528 {
        part def Sensor_0528 :> Common::Component {
            attribute :>> mass = 0.23 [kg];
            attribute :>> cost = 38.0;
            attribute range : Real = 128.0;
            port data : Common::DataPort;
        }
        part def Controller_0528 :> Common::Component {
            attribute :>> mass = 1.30 [kg];
            attribute :>> cost = 228.0;
            port supply : Common::PowerPort;
            part sensors : Sensor_0528[2];
            action smooth : Common::Process;
            action forward : Common::Process;
            succession first smooth then forward;
            exhibit state lifecycle : Common::Lifecycle;
        }
        requirement controllerMass_0528 : Common::MassLimit {
            subject component : Controller_0528;
            attribute :>> limit = 2.0 [kg];
        }
    }

    package Subsystem_0529 {
        part def Sensor_0529 :> Common::Component {
            attribute :>> mass = 0.24 [kg];
            attribute :>> cost = 39.0;
            attribute range : Real = 129.0;
            port data : Common::DataPort;
        }
        part def Controller_0529 :> Common::Component {
            attribute :>> mass = 1.40 [kg];
            attribute :>> cost = 229.0;
            port supply : Common::PowerPort;
            part sensors : Sensor_0529[2];
            action smooth : Common::Process;
            action forward : Common::Process;
            succession first smooth then forward;
            exhibit state lifecycle : Common::Lifecycle;
        }
        requirement controllerMass_0529 : Common::MassLimit {
            subject component : Controller_0529;
            attribute :>> limit = 2.0 [kg];
        }
    }

    package Subsystem_0530 {
        part def Sensor_0530 :> Common::Component {
            attribute :>> mass = 0.20 [kg];
            attribute :>> cost = 40.0;
            attribute range : Real = 130.0;
            port data : Common::DataPort;
        }
        part def Controller_0530 :> Common::Component {
            attribute :>> mass = 1.50 [kg];
            attribute :>> cost = 230.0;
            port supply : Common::PowerPort;
            part sensors : Sensor_0530[2];
            action smooth : Common::Process;
            action forward : Common::Process;
            succession first smooth then forward;
            exhibit state lifecycle : Common::Lifecycle;
        }
        requirement controllerMass_0530 : Common::MassLimit {
            subject component : Controller_0530;
            attribute :>> limit = 2.0 [kg];
        }
    }

    package Subsystem_0531 {
        part def Sensor_0531 :> Common::Component {
            attribute :>> mass = 0.21 [kg];
            attribute :>> cost = 41.0;
            attribute range : Real = 131.0;
            port data : Common::DataPort;
        }
        part def Controller_0531 :> Common::Component {
            attribute :>> mass = 1.60 [kg];
            attribute :>> cost = 231.0;
            port supply : Common::PowerPort;
            part sensors : Sensor_0531[2];
            action smooth : Common::Process;
            action forward : Common::Process;
            succession first smooth then forward;
            exhibit state lifecycle : Common::Lifecycle;
        }
        requirement controllerMass_0531 : Common::MassLimit {
            subject component : Controller_0531;
            attribute :>> limit = 2.0 [kg];
        }
    }

    package Subsystem_0532 {
        part def Sensor_0532 :> Common::Component {
            attribute :>> mass = 0.22 [kg];
            attribute :>> cost = 42.0;
            attribute range : Real = 132.0;
            port data : Common::DataPort;
        }
        part def Controller_0532 :> Common::Component {
            attribute :>> mass = 1.00 [kg];
            attribute :>> cost = 232.0;
            port supply : Common::PowerPort;
            part sensors : Sensor_0532[2];
            action smooth : Common::Process;
            action forward : Common::Process;
            succession first smooth then forward;
            exhibit state lifecycle : Common::Lifecycle;
        }
        requirement controllerMass_0532 : Common::MassLimit {
            subject component : Controller_0532;
            attribute :>> limit = 2.0 [kg];
        }
    }

    package Subsystem_0533 {
        part def Sensor_0533 :> Common::Component {
            attribute :>> mass = 0.23 [kg];
            attribute :>> cost = 43.0;
            attribute range : Real = 133.0;
            port data : Common::DataPort;
        }
        part def Controller_0533 :> Common::Component {
            attribute :>> mass = 1.10 [kg];
            attribute :>> cost = 233.0;
            port supply : Common::PowerPort;
            part sensors : Sensor_0533[2];
            action smooth : Common::Process;
            action forward : Common::Process;
            succession first smooth then forward;
            exhibit state lifecycle : Common::Lifecycle;
        }
        requirement controllerMass_0533 : Common::MassLimit {
            subject component : Controller_0533;
            attribute :>> limit = 2.0 [kg];
        }
    }

    package Subsystem_0534 {
        part def Sensor_0534 :> Common::Component {
            attribute :>> mass = 0.24 [kg];
            attribute :>> cost = 44.0;
            attribute range : Real = 134.0;
            port data : Common::DataPort;
        }
        part def Controller_0534 :> Common::Component {
            attribute :>> mass = 1.20 [kg];
            attribute :>> cost = 234.0;
            port supply : Common::PowerPort;
            part sensors : Sensor_0534[2];
            action smooth : Common::Process;
            action forward : Common::Process;
            succession first smooth then forward;
            exhibit state lifecycle : Common::Lifecycle;
        }
        requirement controllerMass_0534 : Common::MassLimit {
            subject component : Controller_0534;
            attribute :>> limit = 2.0 [kg];
        }
    }

    package Subsystem_0535 {
        part def Sensor_0535 :> Common::Component {
            attribute :>> mass = 0.20 [kg];
            attribute :>> cost = 45.0;
            attribute range : Real = 135.0;
            port data : Common::DataPort;
        }
        part def Controller_0535 :> Common::Component {
            attribute :>> mass = 1.30 [kg];
            attribute :>> cost = 235.0;
            port supply : Common::PowerPort;
            part sensors : Sensor_0535[2];
            action smooth : Common::Process;
            action forward : Common::Process;
            succession first smooth then forward;
            exhibit state lifecycle : Common::Lifecycle;
        }
        requirement controllerMass_0535 : Common::MassLimit {
            subject component : Controller_0535;
            attribute :>> limit = 2.0 [kg];
        }
    }

    package Subsystem_0536 {
        part def Sensor_0536 :> Common::Component {
            attribute :>> mass = 0.21 [kg];
            attribute :>> cost = 46.0;
            attribute range : Real = 136.0;
            port data : Common::DataPort;
        }
        part def Controller_0536 :> Common::Component {
            attribute :>> mass = 1.40 [kg];
            attribute :>> cost = 236.0;
            port supply : Common::PowerPort;
            part sensors : Sensor_0536[2];
            action smooth : Common::Process;
            action forward : Common::Process;
            succession first smooth then forward;
            exhibit state lifecycle : Common::Lifecycle;
        }
        requirement controllerMass_0536 : Common::MassLimit {
            subject component : Controller_0536;
            attribute :>> limit = 2.0 [kg];
        }
    }

    package Subsystem_0537 {
        part def Sensor_0537 :> Common::Component {
            attribute :>> mass = 0.22 [kg];
            attribute :>> cost = 47.0;
            attribute range : Real = 137.0;
            port data : Common::DataPort;
        }
        part def Controller_0537 :> Common::Component {
            attribute :>> mass = 1.50 [kg];
            attribute :>> cost = 237.0;
            port supply : Common::PowerPort;
            part sensors : Sensor_0537[2];
            action smooth : Common::Process;
            action forward : Common::Process;
            succession first smooth then forward;
            exhibit state lifecycle : Common::Lifecycle;
        }
        requirement controllerMass_0537 : Common::MassLimit {
            subject component : Controller_0537;
            attribute :>> limit = 2.0 [kg];
        }
    }

    package Subsystem_0538 {
        part def Sensor_0538 :> Common::Component {
            attribute :>> mass = 0.23 [kg];
            attribute :>> cost = 48.0;
            attribute range : Real = 138.0;
            port data : Common::DataPort;
        }
        part def Controller_0538 :> Common::Component {
            attribute :>> mass = 1.60 [kg];
            attribute :>> cost = 238.0;
            port supply : Common::PowerPort;
            part sensors : Sensor_0538[2];
            action smooth : Common::Process;
            action forward : Common::Process;
            succession first smooth then forward;
            exhibit state lifecycle : Common::Lifecycle;
        }
        requirement controllerMass_0538 : Common::MassLimit {
            subject component : Controller_0538;
            attribute :>> limit = 2.0 [kg];
        }
    }

    package Subsystem_0539 {
        part def Sensor_0539 :> Common::Component {
            attribute :>> mass = 0.24 [kg];
            attribute :>> cost = 49.0;
            attribute range : Real = 139.0;
            port data : Common::DataPort;
        }
        part def Controller_0539 :> Common::Component {
            attribute :>> mass = 1.00 [kg];
            attribute :>> cost = 239.0;
            port supply : Common::PowerPort;
            part sensors : Sensor_0539[2];
            action smooth : Common::Process;
            action forward : Common::Process;
            succession first smooth then forward;
            exhibit state lifecycle : Common::Lifecycle;
        }
        requirement controllerMass_0539 : Common::MassLimit {
            subject component : Controller_0539;
            attribute :>> limit = 2.0 [kg];
        }
    }

    package Subsystem_0540 {
        part def Sensor_0540 :> Common::Component {
            attribute :>> mass = 0.20 [kg];
            attribute :>> cost = 30.0;
            attribute range : Real = 140.0;
            port data : Common::DataPort;
        }
        part def Controller_0540 :> Common::Component {
            attribute :>> mass = 1.10 [kg];
            attribute :>> cost = 240.0;
            port supply : Common::PowerPort;
            part sensors : Sensor_0540[2];
            action smooth : Common::Process;
            action forward : Common::Process;
            succession first smooth then forward;
            exhibit state lifecycle : Common::Lifecycle;
        }
        requirement controllerMass_0540 : Common::MassLimit {
            subject component : Controller_0540;
            attribute :>> limit = 2.0 [kg];
        }
    }

    package Subsystem_0541 {
        part def Sensor_0541 :> Common::Component {
            attribute :>> mass = 0.21 [kg];
            attribute :>> cost = 31.0;
            attribute range : Real = 141.0;
            port data : Common::DataPort;
        }
        part def Controller_0541 :> Common::Component {
            attribute :>> mass = 1.20 [kg];
            attribute :>> cost = 241.0;
            port supply : Common::PowerPort;
            part sensors : Sensor_0541[2];
            action smooth : Common::Process;
            action forward : Common::Process;
            succession first smooth then forward;
            exhibit state lifecycle : Common::Lifecycle;
        }
        requirement controllerMass_0541 : Common::MassLimit {
            subject component : Controller_0541;
            attribute :>> limit = 2.0 [kg];
        }
    }

    package Subsystem_0542 {
        part def Sensor_0542 :> Common::Component {
            attribute :>> mass = 0.22 [kg];
            attribute :>> cost = 32.0;
            attribute range : Real = 142.0;
            port data : Common::DataPort;
        }
        part def Controller_0542 :> Common::Component {
            attribute :>> mass = 1.30 [kg];
            attribute :>> cost = 242.0;
            port supply : Common::PowerPort;
            part sensors : Sensor_0542[2];
            action smooth : Common::Process;
            action forward : Common::Process;
            succession first smooth then forward;
            exhibit state lifecycle : Common::Lifecycle;
        }
        requirement controllerMass_0542 : Common::MassLimit {
            subject component : Controller_0542;
            attribute :>> limit = 2.0 [kg];
        }
    }

    package Subsystem_0543 {
        part def Sensor_0543 :> Common::Component {
            attribute :>> mass = 0.23 [kg];
            attribute :>> cost = 33.0;
            attribute range : Real = 143.0;
            port data : Common::DataPort;
        }
        part def Controller_0543 :> Common::Component {
            attribute :>> mass = 1.40 [kg];
            attribute :>> cost = 243.0;
            port supply : Common::PowerPort;
            part sensors : Sensor_0543[2];
            action smooth : Common::Process;
            action forward : Common::Process;
            succession first smooth then forward;
            exhibit state lifecycle : Common::Lifecycle;
        }
        requirement controllerMass_0543 : Common::MassLimit {
            subject component : Controller_0543;
            attribute :>> limit = 2.0 [kg];
        }
    }

    package Subsystem_0544 {
        part def Sensor_0544 :> Common::Component {
            attribute :>> mass = 0.24 [kg];
            attribute :>> cost = 34.0;
            attribute range : Real = 144.0;
            port data : Common::DataPort;
        }
        part def Controller_0544 :> Common::Component {
            attribute :>> mass = 1.50 [kg];
            attribute :>> cost = 244.0;
            port supply : Common::PowerPort;
            part sensors : Sensor_0544[2];
            action smooth : Common::Process;
            action forward : Common::Process;
            succession first smooth then forward;
            exhibit state lifecycle : Common::Lifecycle;
        }
        requirement controllerMass_0544 : Common::MassLimit {
            subject component : Controller_0544;
            attribute :>> limit = 2.0 [kg];
        }
    }

    package Subsystem_0545 {
        part def Sensor_0545 :> Common::Component {
            attribute :>> mass = 0.20 [kg];
            attribute :>> cost = 35.0;
            attribute range : Real = 145.0;
            port data : Common::DataPort;
        }
        part def Controller_0545 :> Common::Component {
            attribute :>> mass = 1.60 [kg];
            attribute :>> cost = 245.0;
            port supply : Common::PowerPort;
            part sensors : Sensor_0545[2];
            action smooth : Common::Process;
            action forward : Common::Process;
            succession first smooth then forward;
            exhibit state lifecycle : Common::Lifecycle;
        }
        requirement controllerMass_0545 : Common::MassLimit {
            subject component : Controller_0545;
            attribute :>> limit = 2.0 [kg];
        }
    }

    package Subsystem_0546 {
        part def Sensor_0546 :> Common::Component {
            attribute :>> mass = 0.21 [kg];
            attribute :>> cost = 36.0;
            attribute range : Real = 146.0;
            port data : Common::DataPort;
        }
        part def Controller_0546 :> Common::Component {
            attribute :>> mass = 1.00 [kg];
            attribute :>> cost = 246.0;
            port supply : Common::PowerPort;
            part sensors : Sensor_0546[2];
            action smooth : Common::Process;
            action forward : Common::Process;
            succession first smooth then forward;
            exhibit state lifecycle : Common::Lifecycle;
        }
        requirement controllerMass_0546 : Common::MassLimit {
            subject component : Controller_0546;
            attribute :>> limit = 2.0 [kg];
        }
    }

    package Subsystem_0547 {
        part def Sensor_0547 :> Common::Component {
            attribute :>> mass = 0.22 [kg];
            attribute :>> cost = 37.0;
            attribute range : Real = 147.0;
            port data : Common::DataPort;
        }
        part def Controller_0547 :> Common::Component {
            attribute :>> mass = 1.10 [kg];
            attribute :>> cost = 247.0;
            port supply : Common::PowerPort;
            part sensors : Sensor_0547[2];
            action smooth : Common::Process;
            action forward : Common::Process;
            succession first smooth then forward;
            exhibit state lifecycle : Common::Lifecycle;
        }
        requirement controllerMass_0547 : Common::MassLimit {
            subject component : Controller_0547;
            attribute :>> limit = 2.0 [kg];
        }
    }

    package Subsystem_0548 {
        part def Sensor_0548 :> Common::Component {
            attribute :>> mass = 0.23 [kg];
            attribute :>> cost = 38.0;
            attribute range : Real = 148.0;
            port data : Common::DataPort;
        }
        part def Controller_0548 :> Common::Component {
            attribute :>> mass = 1.20 [kg];
            attribute :>> cost = 248.0;
            port supply : Common::PowerPort;
            part sensors : Sensor_0548[2];
            action smooth : Common::Process;
            action forward : Common::Process;
            succession first smooth then forward;
            exhibit state lifecycle : Common::Lifecycle;
        }
        requirement controllerMass_0548 : Common::MassLimit {
            subject component : Controller_0548;
            attribute :>> limit = 2.0 [kg];
        }
    }

    package Subsystem_0549 {
        part def Sensor_0549 :> Common::Component {
            attribute :>> mass = 0.24 [kg];
            attribute :>> cost = 39.0;
            attribute range : Real = 149.0;
            port data : Common::DataPort;
        }
        part def Controller_0549 :> Common::Component {
            attribute :>> mass = 1.30 [kg];
            attribute :>> cost = 249.0;
            port supply : Common::PowerPort;
            part sensors : Sensor_0549[2];
            action smooth : Common::Process;
            action forward : Common::Process;
            succession first smooth then forward;
            exhibit state lifecycle : Common::Lifecycle;
        }
        requirement controllerMass_0549 : Common::MassLimit {
            subject component : Controller_0549;
            attribute :>> limit = 2.0 [kg];
        }
    }

    package Subsystem_0550 {
        part def Sensor_0550 :> Common::Component {
            attribute :>> mass = 0.20 [kg];
            attribute :>> cost = 40.0;
            attribute range : Real = 100.0;
            port data : Common::DataPort;
        }
        part def Controller_0550 :> Common::Component {
            attribute :>> mass = 1.40 [kg];
            attribute :>> cost = 250.0;
            port supply : Common::PowerPort;
            part sensors : Sensor_0550[2];
            action smooth : Common::Process;
            action forward : Common::Process;
            succession first smooth then forward;
            exhibit state lifecycle : Common::Lifecycle;
        }
        requirement controllerMass_0550 : Common::MassLimit {
            subject component : Controller_0550;
            attribute :>> limit = 2.0 [kg];
        }
    }

    package Subsystem_0551 {
        part def Sensor_0551 :> Common::Component {
            attribute :>> mass = 0.21 [kg];
            attribute :>> cost = 41.0;
            attribute range : Real = 101.0;
            port data : Common::DataPort;
        }
        part def Controller_0551 :> Common::Component {
            attribute :>> mass = 1.50 [kg];
            attribute :>> cost = 251.0;
            port supply : Common::PowerPort;
            part sensors : Sensor_0551[2];
            action smooth : Common::Process;
            action forward : Common::Process;
            succession first smooth then forward;
            exhibit state lifecycle : Common::Lifecycle;
        }
        requirement controllerMass_0551 : Common::MassLimit {
            subject component : Controller_0551;
            attribute :>> limit = 2.0 [kg];
        }
    }

    package Subsystem_0552 {
        part def Sensor_0552 :> Common::Component {
            attribute :>> mass = 0.22 [kg];
            attribute :>> cost = 42.0;
            attribute range : Real = 102.0;
            port data : Common::DataPort;
        }
        part def Controller_0552 :> Common::Component {
            attribute :>> mass = 1.60 [kg];
            attribute :>> cost = 252.0;
            port supply : Common::PowerPort;
            part sensors : Sensor_0552[2];
            action smooth : Common::Process;
            action forward : Common::Process;
            succession first smooth then forward;
            exhibit state lifecycle : Common::Lifecycle;
        }
        requirement controllerMass_0552 : Common::MassLimit {
            subject component : Controller_0552;
            attribute :>> limit = 2.0 [kg];
        }
    }

    package Subsystem_0553 {
        part def Sensor_0553 :> Common::Component {
            attribute :>> mass = 0.23 [kg];
            attribute :>> cost = 43.0;
            attribute range : Real = 103.0;
            port data : Common::DataPort;
        }
        part def Controller_0553 :> Common::Component {
            attribute :>> mass = 1.00 [kg];
            attribute :>> cost = 253.0;
            port supply : Common::PowerPort;
            part sensors : Sensor_0553[2];
            action smooth : Common::Process;
            action forward : Common::Process;
            succession first smooth then forward;
            exhibit state lifecycle : Common::Lifecycle;
        }
        requirement controllerMass_0553 : Common::MassLimit {
            subject component : Controller_0553;
            attribute :>> limit = 2.0 [kg];
        }
    }

    package Subsystem_0554 {
        part def Sensor_0554 :> Common::Component {
            attribute :>> mass = 0.24 [kg];
            attribute :>> cost = 44.0;
            attribute range : Real = 104.0;
            port data : Common::DataPort;
        }
        part def Controller_0554 :> Common::Component {
            attribute :>> mass = 1.10 [kg];
            attribute :>> cost = 254.0;
            port supply : Common::PowerPort;
            part sensors : Sensor_0554[2];
            action smooth : Common::Process;
            action forward : Common::Process;
            succession first smooth then forward;
            exhibit state lifecycle : Common::Lifecycle;
        }
        requirement controllerMass_0554 : Common::MassLimit {
            subject component : Controller_0554;
            attribute :>> limit = 2.0 [kg];
        }
    }

    package Subsystem_0555 {
        part def Sensor_0555 :> Common::Component {
            attribute :>> mass = 0.20 [kg];
            attribute :>> cost = 45.0;
            attribute range : Real = 105.0;
            port data : Common::DataPort;
        }
        part def Controller_0555 :> Common::Component {
            attribute :>> mass = 1.20 [kg];
            attribute :>> cost = 255.0;
            port supply : Common::PowerPort;
            part sensors : Sensor_0555[2];
            action smooth : Common::Process;
            action forward : Common::Process;
            succession first smooth then forward;
            exhibit state lifecycle : Common::Lifecycle;
        }
        requirement controllerMass_0555 : Common::MassLimit {
            subject component : Controller_0555;
            attribute :>> limit = 2.0 [kg];
        }
    }

    package Subsystem_0556 {
        part def Sensor_0556 :> Common::Component {
            attribute :>> mass = 0.21 [kg];
            attribute :>> cost = 46.0;
            attribute range : Real = 106.0;
            port data : Common::DataPort;
        }
        part def Controller_0556 :> Common::Component {
            attribute :>> mass = 1.30 [kg];
            attribute :>> cost = 256.0;
            port supply : Common::PowerPort;
            part sensors : Sensor_0556[2];
            action smooth : Common::Process;
            action forward : Common::Process;
            succession first smooth then forward;
            exhibit state lifecycle : Common::Lifecycle;
        }
        requirement controllerMass_0556 : Common::MassLimit {
            subject component : Controller_0556;
            attribute :>> limit = 2.0 [kg];
        }
    }

    package Subsystem_0557 {
        part def Sensor_0557 :> Common::Component {
            attribute :>> mass = 0.22 [kg];
            attribute :>> cost = 47.0;
            attribute range : Real = 107.0;
            port data : Common::DataPort;
        }
        part def Controller_0557 :> Common::Component {
            attribute :>> mass = 1.40 [kg];
            attribute :>> cost = 257.0;
            port supply : Common::PowerPort;
            part sensors : Sensor_0557[2];
            action smooth : Common::Process;
            action forward : Common::Process;
            succession first smooth then forward;
            exhibit state lifecycle : Common::Lifecycle;
        }
        requirement controllerMass_0557 : Common::MassLimit {
            subject component : Controller_0557;
            attribute :>> limit = 2.0 [kg];
        }
    }

    package Subsystem_0558 {
        part def Sensor_0558 :> Common::Component {
            attribute :>> mass = 0.23 [kg];
            attribute :>> cost = 48.0;
            attribute range : Real = 108.0;
            port data : Common::DataPort;
        }
        part def Controller_0558 :> Common::Component {
            attribute :>> mass = 1.50 [kg];
            attribute :>> cost = 258.0;
            port supply : Common::PowerPort;
            part sensors : Sensor_0558[2];
            action smooth : Common::Process;
            action forward : Common::Process;
            succession first smooth then forward;
            exhibit state lifecycle : Common::Lifecycle;
        }
        requirement controllerMass_0558 : Common::MassLimit {
            subject component : Controller_0558;
            attribute :>> limit = 2.0 [kg];
        }
    }

    package Subsystem_0559 {
        part def Sensor_0559 :> Common::Component {
            attribute :>> mass = 0.24 [kg];
            attribute :>> cost = 49.0;
            attribute range : Real = 109.0;
            port data : Common::DataPort;
        }
        part def Controller_0559 :> Common::Component {
            attribute :>> mass = 1.60 [kg];
            attribute :>> cost = 259.0;
            port supply : Common::PowerPort;
            part sensors : Sensor_0559[2];
            action smooth : Common::Process;
            action forward : Common::Process;
            succession first smooth then forward;
            exhibit state lifecycle : Common::Lifecycle;
        }
        requirement controllerMass_0559 : Common::MassLimit {
            subject component : Controller_0559;
            attribute :>> limit = 2.0 [kg];
        }
    }

    package Subsystem_0560 {
        part def Sensor_0560 :> Common::Component {
            attribute :>> mass = 0.20 [kg];
            attribute :>> cost = 30.0;
            attribute range : Real = 110.0;
            port data : Common::DataPort;
        }
        part def Controller_0560 :> Common::Component {
            attribute :>> mass = 1.00 [kg];
            attribute :>> cost = 260.0;
            port supply : Common::PowerPort;
            part sensors : Sensor_0560[2];
            action smooth : Common::Process;
            action forward : Common::Process;
            succession first smooth then forward;
            exhibit state lifecycle : Common::Lifecycle;
        }
        requirement controllerMass_0560 : Common::MassLimit {
            subject component : Controller_0560;
            attribute :>> limit = 2.0 [kg];
        }
    }

    package Subsystem_0561 {
        part def Sensor_0561 :> Common::Component {
            attribute :>> mass = 0.21 [kg];
            attribute :>> cost = 31.0;
            attribute range : Real = 111.0;
            port data : Common::DataPort;
        }
        part def Controller_0561 :> Common::Component {
            attribute :>> mass = 1.10 [kg];
            attribute :>> cost = 261.0;
            port supply : Common::PowerPort;
            part sensors : Sensor_0561[2];
            action smooth : Common::Process;
            action forward : Common::Process;
            succession first smooth then forward;
            exhibit state lifecycle : Common::Lifecycle;
        }
        requirement controllerMass_0561 : Common::MassLimit {
            subject component : Controller_0561;
            attribute :>> limit = 2.0 [kg];
        }
    }

    package Subsystem_0562 {
        part def Sensor_0562 :> Common::Component {
            attribute :>> mass = 0.22 [kg];
            attribute :>> cost = 32.0;
            attribute range : Real = 112.0;
            port data : Common::DataPort;
        }
        part def Controller_0562 :> Common::Component {
            attribute :>> mass = 1.20 [kg];
            attribute :>> cost = 262.0;
            port supply : Common::PowerPort;
            part sensors : Sensor_0562[2];
            action smooth : Common::Process;
            action forward : Common::Process;
            succession first smooth then forward;
            exhibit state lifecycle : Common::Lifecycle;
        }
        requirement controllerMass_0562 : Common::MassLimit {
            subject component : Controller_0562;
            attribute :>> limit = 2.0 [kg];
        }
    }

    package Subsystem_0563 {
        part def Sensor_0563 :> Common::Component {
            attribute :>> mass = 0.23 [kg];
            attribute :>> cost = 33.0;
            attribute range : Real = 113.0;
            port data : Common::DataPort;
        }
        part def Controller_0563 :> Common::Component {
            attribute :>> mass = 1.30 [kg];
            attribute :>> cost = 263.0;
            port supply : Common::PowerPort;
            part sensors : Sensor_0563[2];
            action smooth : Common::Process;
            action forward : Common::Process;
            succession first smooth then forward;
            exhibit state lifecycle : Common::Lifecycle;
        }
        requirement controllerMass_0563 : Common::MassLimit {
            subject component : Controller_0563;
            attribute :>> limit = 2.0 [kg];
        }
    }

    package Subsystem_0564 {
        part def Sensor_0564 :> Common::Component {
            attribute :>> mass = 0.24 [kg];
            attribute :>> cost = 34.0;
            attribute range : Real = 114.0;
            port data : Common::DataPort;
        }
        part def Controller_0564 :> Common::Component {
            attribute :>> mass = 1.40 [kg];
            attribute :>> cost = 264.0;
            port supply : Common::PowerPort;
            part sensors : Sensor_0564[2];
            action smooth : Common::Process;
            action forward : Common::Process;
            succession first smooth then forward;
            exhibit state lifecycle : Common::Lifecycle;
        }
        requirement controllerMass_0564 : Common::MassLimit {
            subject component : Controller_0564;
            attribute :>> limit = 2.0 [kg];
        }
    }

    package Subsystem_0565 {
        part def Sensor_0565 :> Common::Component {
            attribute :>> mass = 0.20 [kg];
            attribute :>> cost = 35.0;
            attribute range : Real = 115.0;
            port data : Common::DataPort;
        }
        part def Controller_0565 :> Common::Component {
            attribute :>> mass = 1.50 [kg];
            attribute :>> cost = 265.0;
            port supply : Common::PowerPort;
            part sensors : Sensor_0565[2];
            action smooth : Common::Process;
            action forward : Common::Process;
            succession first smooth then forward;
            exhibit state lifecycle : Common::Lifecycle;
        }
        requirement controllerMass_0565 : Common::MassLimit {
            subject component : Controller_0565;
            attribute :>> limit = 2.0 [kg];
        }
    }

    package Subsystem_0566 {
        part def Sensor_0566 :> Common::Component {
            attribute :>> mass = 0.21 [kg];
            attribute :>> cost = 36.0;
            attribute range : Real = 116.0;
            port data : Common::DataPort;
        }
        part def Controller_0566 :> Common::Component {
            attribute :>> mass = 1.60 [kg];
            attribute :>> cost = 266.0;
            port supply : Common::PowerPort;
            part sensors : Sensor_0566[2];
            action smooth : Common::Process;
            action forward : Common::Process;
            succession first smooth then forward;
            exhibit state lifecycle : Common::Lifecycle;
        }
        requirement controllerMass_0566 : Common::MassLimit {
            subject component : Controller_0566;
            attribute :>> limit = 2.0 [kg];
        }
    }

    package Subsystem_0567 {
        part def Sensor_0567 :> Common::Component {
            attribute :>> mass = 0.22 [kg];
            attribute :>> cost = 37.0;
            attribute range : Real = 117.0;
            port data : Common::DataPort;
        }
        part def Controller_0567 :> Common::Component {
            attribute :>> mass = 1.00 [kg];
            attribute :>> cost = 267.0;
            port supply : Common::PowerPort;
            part sensors : Sensor_0567[2];
            action smooth : Common::Process;
            action forward : Common::Process;
            succession first smooth then forward;
            exhibit state lifecycle : Common::Lifecycle;
        }
        requirement controllerMass_0567 : Common::MassLimit {
            subject component : Controller_0567;
            attribute :>> limit = 2.0 [kg];
        }
    }

    package Subsystem_0568 {
        part def Sensor_0568 :> Common::Component {
            attribute :>> mass = 0.23 [kg];
            attribute :>> cost = 38.0;
            attribute range : Real = 118.0;
            port data : Common::DataPort;
        }
        part def Controller_0568 :> Common::Component {
            attribute :>> mass = 1.10 [kg];
            attribute :>> cost = 268.0;
            port supply : Common::PowerPort;
            part sensors : Sensor_0568[2];
            action smooth : Common::Process;
            action forward : Common::Process;
            succession first smooth then forward;
            exhibit state lifecycle : Common::Lifecycle;
        }
        requirement controllerMass_0568 : Common::MassLimit {
            subject component : Controller_0568;
            attribute :>> limit = 2.0 [kg];
        }
    }

    package Subsystem_0569 {
        part def Sensor_0569 :> Common::Component {
            attribute :>> mass = 0.24 [kg];
            attribute :>> cost = 39.0;
            attribute range : Real = 119.0;
            port data : Common::DataPort;
        }
        part def Controller_0569 :> Common::Component {
            attribute :>> mass = 1.20 [kg];
            attribute :>> cost = 269.0;
            port supply : Common::PowerPort;
            part sensors : Sensor_0569[2];
            action smooth : Common::Process;
            action forward : Common::Process;
            succession first smooth then forward;
            exhibit state lifecycle : Common::Lifecycle;
        }
        requirement controllerMass_0569 : Common::MassLimit {
            subject component : Controller_0569;
            attribute :>> limit = 2.0 [kg];
        }
    }

    package Subsystem_0570 {
        part def Sensor_0570 :> Common::Component {
            attribute :>> mass = 0.20 [kg];
            attribute :>> cost = 40.0;
            attribute range : Real = 120.0;
            port data : Common::DataPort;
        }
        part def Controller_0570 :> Common::Component {
            attribute :>> mass = 1.30 [kg];
            attribute :>> cost = 270.0;
            port supply : Common::PowerPort;
            part sensors : Sensor_0570[2];
            action smooth : Common::Process;
            action forward : Common::Process;
            succession first smooth then forward;
            exhibit state lifecycle : Common::Lifecycle;
        }
        requirement controllerMass_0570 : Common::MassLimit {
            subject component : Controller_0570;
            attribute :>> limit = 2.0 [kg];
        }
    }

    package Subsystem_0571 {
        part def Sensor_0571 :> Common::Component {
            attribute :>> mass = 0.21 [kg];
            attribute :>> cost = 41.0;
            attribute range : Real = 121.0;
            port data : Common::DataPort;
        }
        part def Controller_0571 :> Common::Component {
            attribute :>> mass = 1.40 [kg];
            attribute :>> cost = 271.0;
            port supply : Common::PowerPort;
            part sensors : Sensor_0571[2];
            action smooth : Common::Process;
            action forward : Common::Process;
            succession first smooth then forward;
            exhibit state lifecycle : Common::Lifecycle;
        }
        requirement controllerMass_0571 : Common::MassLimit {
            subject component : Controller_0571;
            attribute :>> limit = 2.0 [kg];
        }
    }

    package Subsystem_0572 {
        part def Sensor_0572 :> Common::Component {
            attribute :>> mass = 0.22 [kg];
            attribute :>> cost = 42.0;
            attribute range : Real = 122.0;
            port data : Common::DataPort;
        }
        part def Controller_0572 :> Common::Component {
            attribute :>> mass = 1.50 [kg];
            attribute :>> cost = 272.0;
            port supply : Common::PowerPort;
            part sensors : Sensor_0572[2];
            action smooth : Common::Process;
            action forward : Common::Process;
            succession first smooth then forward;
            exhibit state lifecycle : Common::Lifecycle;
        }
        requirement controllerMass_0572 : Common::MassLimit {
            subject component : Controller_0572;
            attribute :>> limit = 2.0 [kg];
        }
    }

    package Subsystem_0573 {
        part def Sensor_0573 :> Common::Component {
            attribute :>> mass = 0.23 [kg];
            attribute :>> cost = 43.0;
            attribute range : Real = 123.0;
            port data : Common::DataPort;
        }
        part def Controller_0573 :> Common::Component {
            attribute :>> mass = 1.60 [kg];
            attribute :>> cost = 273.0;
            port supply : Common::PowerPort;
            part sensors : Sensor_0573[2];
            action smooth : Common::Process;
            action forward : Common::Process;
            succession first smooth then forward;
            exhibit state lifecycle : Common::Lifecycle;
        }
        requirement controllerMass_0573 : Common::MassLimit {
            subject component : Controller_0573;
            attribute :>> limit = 2.0 [kg];
        }
    }

    package Subsystem_0574 {
        part def Sensor_0574 :> Common::Component {
            attribute :>> mass = 0.24 [kg];
            attribute :>> cost = 44.0;
            attribute range : Real = 124.0;
            port data : Common::DataPort;
        }
        part def Controller_0574 :> Common::Component {
            attribute :>> mass = 1.00 [kg];
            attribute :>> cost = 274.0;
            port supply : Common::PowerPort;
            part sensors : Sensor_0574[2];
            action smooth : Common::Process;
            action forward : Common::Process;
            succession first smooth then forward;
            exhibit state lifecycle : Common::Lifecycle;
        }
        requirement controllerMass_0574 : Common::MassLimit {
            subject component : Controller_0574;
            attribute :>> limit = 2.0 [kg];
        }
    }

    package Subsystem_0575 {
        part def Sensor_0575 :> Common::Component {
            attribute :>> mass = 0.20 [kg];
            attribute :>> cost = 45.0;
            attribute range : Real = 125.0;
            port data : Common::DataPort;
        }
        part def Controller_0575 :> Common::Component {
            attribute :>> mass = 1.10 [kg];
            attribute :>> cost = 275.0;
            port supply : Common::PowerPort;
            part sensors : Sensor_0575[2];
            action smooth : Common::Process;
            action forward : Common::Process;
            succession first smooth then forward;
            exhibit state lifecycle : Common::Lifecycle;
        }
        requirement controllerMass_0575 : Common::MassLimit {
            subject component : Controller_0575;
            attribute :>> limit = 2.0 [kg];
        }
    }

    package Subsystem_0576 {
        part def Sensor_0576 :> Common::Component {
            attribute :>> mass = 0.21 [kg];
            attribute :>> cost = 46.0;
            attribute range : Real = 126.0;
            port data : Common::DataPort;
        }
        part def Controller_0576 :> Common::Component {
            attribute :>> mass = 1.20 [kg];
            attribute :>> cost = 276.0;
            port supply : Common::PowerPort;
            part sensors : Sensor_0576[2];
            action smooth : Common::Process;
            action forward : Common::Process;
            succession first smooth then forward;
            exhibit state lifecycle : Common::Lifecycle;
        }
        requirement controllerMass_0576 : Common::MassLimit {
            subject component : Controller_0576;
            attribute :>> limit = 2.0 [kg];
        }
    }

    package Subsystem_0577 {
        part def Sensor_0577 :> Common::Component {
            attribute :>> mass = 0.22 [kg];
            attribute :>> cost = 47.0;
            attribute range : Real = 127.0;
            port data : Common::DataPort;
        }
        part def Controller_0577 :> Common::Component {
            attribute :>> mass = 1.30 [kg];
            attribute :>> cost = 277.0;
            port supply : Common::PowerPort;
            part sensors : Sensor_0577[2];
            action smooth : Common::Process;
            action forward : Common::Process;
            succession first smooth then forward;
            exhibit state lifecycle : Common::Lifecycle;
        }
        requirement controllerMass_0577 : Common::MassLimit {
            subject component : Controller_0577;
            attribute :>> limit = 2.0 [kg];
        }
    }

    package Subsystem_0578 {
        part def Sensor_0578 :> Common::Component {
            attribute :>> mass = 0.23 [kg];
            attribute :>> cost = 48.0;
            attribute range : Real = 128.0;
            port data : Common::DataPort;
        }
        part def Controller_0578 :> Common::Component {
            attribute :>> mass = 1.40 [kg];
            attribute :>> cost = 278.0;
            port supply : Common::PowerPort;
            part sensors : Sensor_0578[2];
            action smooth : Common::Process;
            action forward : Common::Process;
            succession first smooth then forward;
            exhibit state lifecycle : Common::Lifecycle;
        }
        requirement controllerMass_0578 : Common::MassLimit {
            subject component : Controller_0578;
            attribute :>> limit = 2.0 [kg];
        }
    }

    package Subsystem_0579 {
        part def Sensor_0579 :> Common::Component {
            attribute :>> mass = 0.24 [kg];
            attribute :>> cost = 49.0;
            attribute range : Real = 129.0;
            port data : Common::DataPort;
        }
        part def Controller_0579 :> Common::Component {
            attribute :>> mass = 1.50 [kg];
            attribute :>> cost = 279.0;
            port supply : Common::PowerPort;
            part sensors : Sensor_0579[2];
            action smooth : Common::Process;
            action forward : Common::Process;
            succession first smooth then forward;
            exhibit state lifecycle : Common::Lifecycle;
        }
        requirement controllerMass_0579 : Common::MassLimit {
            subject component : Controller_0579;
            attribute :>> limit = 2.0 [kg];
        }
    }

    package Subsystem_0580 {
        part def Sensor_0580 :> Common::Component {
            attribute :>> mass = 0.20 [kg];
            attribute :>> cost = 30.0;
            attribute range : Real = 130.0;
            port data : Common::DataPort;
        }
        part def Controller_0580 :> Common::Component {
            attribute :>> mass = 1.60 [kg];
            attribute :>> cost = 280.0;
            port supply : Common::PowerPort;
            part sensors : Sensor_0580[2];
            action smooth : Common::Process;
            action forward : Common::Process;
            succession first smooth then forward;
            exhibit state lifecycle : Common::Lifecycle;
        }
        requirement controllerMass_0580 : Common::MassLimit {
            subject component : Controller_0580;
            attribute :>> limit = 2.0 [kg];
        }
    }

    package Subsystem_0581 {
        part def Sensor_0581 :> Common::Component {
            attribute :>> mass = 0.21 [kg];
            attribute :>> cost = 31.0;
            attribute range : Real = 131.0;
            port data : Common::DataPort;
        }
        part def Controller_0581 :> Common::Component {
            attribute :>> mass = 1.00 [kg];
            attribute :>> cost = 281.0;
            port supply : Common::PowerPort;
            part sensors : Sensor_0581[2];
            action smooth : Common::Process;
            action forward : Common::Process;
            succession first smooth then forward;
            exhibit state lifecycle : Common::Lifecycle;
        }
        requirement controllerMass_0581 : Common::MassLimit {
            subject component : Controller_0581;
            attribute :>> limit = 2.0 [kg];
        }
    }

    package Subsystem_0582 {
        part def Sensor_0582 :> Common::Component {
            attribute :>> mass = 0.22 [kg];
            attribute :>> cost = 32.0;
            attribute range : Real = 132.0;
            port data : Common::DataPort;
        }
        part def Controller_0582 :> Common::Component {
            attribute :>> mass = 1.10 [kg];
            attribute :>> cost = 282.0;
            port supply : Common::PowerPort;
            part sensors : Sensor_0582[2];
            action smooth : Common::Process;
            action forward : Common::Process;
            succession first smooth then forward;
            exhibit state lifecycle : Common::Lifecycle;
        }
        requirement controllerMass_0582 : Common::MassLimit {
            subject component : Controller_0582;
            attribute :>> limit = 2.0 [kg];
        }
    }

    package Subsystem_0583 {
        part def Sensor_0583 :> Common::Component {
            attribute :>> mass = 0.23 [kg];
            attribute :>> cost = 33.0;
            attribute range : Real = 133.0;
            port data : Common::DataPort;
        }
        part def Controller_0583 :> Common::Component {
            attribute :>> mass = 1.20 [kg];
            attribute :>> cost = 283.0;
            port supply : Common::PowerPort;
            part sensors : Sensor_0583[2];
            action smooth : Common::Process;
            action forward : Common::Process;
            succession first smooth then forward;
            exhibit state lifecycle : Common::Lifecycle;
        }
        requirement controllerMass_0583 : Common::MassLimit {
            subject component : Controller_0583;
            attribute :>> limit = 2.0 [kg];
        }
    }

    package Subsystem_0584 {
        part def Sensor_0584 :> Common::Component {
            attribute :>> mass = 0.24 [kg];
            attribute :>> cost = 34.0;
            attribute range : Real = 134.0;
            port data : Common::DataPort;
        }
        part def Controller_0584 :> Common::Component {
            attribute :>> mass = 1.30 [kg];
            attribute :>> cost = 284.0;
            port supply : Common::PowerPort;
            part sensors : Sensor_0584[2];
            action smooth : Common::Process;
            action forward : Common::Process;
            succession first smooth then forward;
            exhibit state lifecycle : Common::Lifecycle;
        }
        requirement controllerMass_0584 : Common::MassLimit {
            subject component : Controller_0584;
            attribute :>> limit = 2.0 [kg];
        }
    }

    package Subsystem_0585 {
        part def Sensor_0585 :> Common::Component {
            attribute :>> mass = 0.20 [kg];
            attribute :>> cost = 35.0;
            attribute range : Real = 135.0;
            port data : Common::DataPort;
        }
        part def Controller_0585 :> Common::Component {
            attribute :>> mass = 1.40 [kg];
            attribute :>> cost = 285.0;
            port supply : Common::PowerPort;
            part sensors : Sensor_0585[2];
            action smooth : Common::Process;
            action forward : Common::Process;
            succession first smooth then forward;
            exhibit state lifecycle : Common::Lifecycle;
        }
        requirement controllerMass_0585 : Common::MassLimit {
            subject component : Controller_0585;
            attribute :>> limit = 2.0 [kg];
        }
    }

    package Subsystem_0586 {
        part def Sensor_0586 :> Common::Component {
            attribute :>> mass = 0.21 [kg];
            attribute :>> cost = 36.0;
            attribute range : Real = 136.0;
            port data : Common::DataPort;
        }
        part def Controller_0586 :> Common::Component {
            attribute :>> mass = 1.50 [kg];
            attribute :>> cost = 286.0;
            port supply : Common::PowerPort;
            part sensors : Sensor_0586[2];
            action smooth : Common::Process;
            action forward : Common::Process;
            succession first smooth then forward;
            exhibit state lifecycle : Common::Lifecycle;
        }
        requirement controllerMass_0586 : Common::MassLimit {
            subject component : Controller_0586;
            attribute :>> limit = 2.0 [kg];
        }
    }

    package Subsystem_0587 {
        part def Sensor_0587 :> Common::Component {
            attribute :>> mass = 0.22 [kg];
            attribute :>> cost = 37.0;
            attribute range : Real = 137.0;
            port data : Common::DataPort;
        }
        part def Controller_0587 :> Common::Component {
            attribute :>> mass = 1.60 [kg];
            attribute :>> cost = 287.0;
            port supply : Common::PowerPort;
            part sensors : Sensor_0587[2];
            action smooth : Common::Process;
            action forward : Common::Process;
            succession first smooth then forward;
            exhibit state lifecycle : Common::Lifecycle;
        }
        requirement controllerMass_0587 : Common::MassLimit {
            subject component : Controller_0587;
            attribute :>> limit = 2.0 [kg];
        }
    }

    package Subsystem_0588 {
        part def Sensor_0588 :> Common::Component {
            attribute :>> mass = 0.23 [kg];
            attribute :>> cost = 38.0;
            attribute range : Real = 138.0;
            port data : Common::DataPort;
        }
        part def Controller_0588 :> Common::Component {
            attribute :>> mass = 1.00 [kg];
            attribute :>> cost = 288.0;
            port supply : Common::PowerPort;
            part sensors : Sensor_0588[2];
            action smooth : Common::Process;
            action forward : Common::Process;
            succession first smooth then forward;
            exhibit state lifecycle : Common::Lifecycle;
        }
        requirement controllerMass_0588 : Common::MassLimit {
            subject component : Controller_0588;
            attribute :>> limit = 2.0 [kg];
        }
    }

    package Subsystem_0589 {
        part def Sensor_0589 :> Common::Component {
            attribute :>> mass = 0.24 [kg];
            attribute :>> cost = 39.0;
            attribute range : Real = 139.0;
            port data : Common::DataPort;
        }
        part def Controller_0589 :> Common::Component {
            attribute :>> mass = 1.10 [kg];
            attribute :>> cost = 289.0;
            port supply : Common::PowerPort;
            part sensors : Sensor_0589[2];
            action smooth : Common::Process;
            action forward : Common::Process;
            succession first smooth then forward;
            exhibit state lifecycle : Common::Lifecycle;
        }
        requirement controllerMass_0589 : Common::MassLimit {
            subject component : Controller_0589;
            attribute :>> limit = 2.0 [kg];
        }
    }

    package Subsystem_0590 {
        part def Sensor_0590 :> Common::Component {
            attribute :>> mass = 0.20 [kg];
            attribute :>> cost = 40.0;
            attribute range : Real = 140.0;
            port data : Common::DataPort;
        }
        part def Controller_0590 :> Common::Component {
            attribute :>> mass = 1.20 [kg];
            attribute :>> cost = 290.0;
            port supply : Common::PowerPort;
            part sensors : Sensor_0590[2];
            action smooth : Common::Process;
            action forward : Common::Process;
            succession first smooth then forward;
            exhibit state lifecycle : Common::Lifecycle;
        }
        requirement controllerMass_0590 : Common::MassLimit {
            subject component : Controller_0590;
            attribute :>> limit = 2.0 [kg];
        }
    }

    package Subsystem_0591 {
        part def Sensor_0591 :> Common::Component {
            attribute :>> mass = 0.21 [kg];
            attribute :>> cost = 41.0;
            attribute range : Real = 141.0;
            port data : Common::DataPort;
        }
        part def Controller_0591 :> Common::Component {
            attribute :>> mass = 1.30 [kg];
            attribute :>> cost = 291.0;
            port supply : Common::PowerPort;
            part sensors : Sensor_0591[2];
            action smooth : Common::Process;
            action forward : Common::Process;
            succession first smooth then forward;
            exhibit state lifecycle : Common::Lifecycle;
        }
        requirement controllerMass_0591 : Common::MassLimit {
            subject component : Controller_0591;
            attribute :>> limit = 2.0 [kg];
        }
    }

    package Subsystem_0592 {
        part def Sensor_0592 :> Common::Component {
            attribute :>> mass = 0.22 [kg];
            attribute :>> cost = 42.0;
            attribute range : Real = 142.0;
            port data : Common::DataPort;
        }
        part def Controller_0592 :> Common::Component {
            attribute :>> mass = 1.40 [kg];
            attribute :>> cost = 292.0;
            port supply : Common::PowerPort;
            part sensors : Sensor_0592[2];
            action smooth : Common::Process;
            action forward : Common::Process;
            succession first smooth then forward;
            exhibit state lifecycle : Common::Lifecycle;
        }
        requirement controllerMass_0592 : Common::MassLimit {
            subject component : Controller_0592;
            attribute :>> limit = 2.0 [kg];
        }
    }

    package Subsystem_0593 {
        part def Sensor_0593 :> Common::Component {
            attribute :>> mass = 0.23 [kg];
            attribute :>> cost = 43.0;
            attribute range : Real = 143.0;
            port data : Common::DataPort;
        }
        part def Controller_0593 :> Common::Component {
            attribute :>> mass = 1.50 [kg];
            attribute :>> cost = 293.0;
            port supply : Common::PowerPort;
            part sensors : Sensor_0593[2];
            action smooth : Common::Process;
            action forward : Common::Process;
            succession first smooth then forward;
            exhibit state lifecycle : Common::Lifecycle;
        }
        requirement controllerMass_0593 : Common::MassLimit {
            subject component : Controller_0593;
            attribute :>> limit = 2.0 [kg];
        }
    }

    package Subsystem_0594 {
        part def Sensor_0594 :> Common::Component {
            attribute :>> mass = 0.24 [kg];
            attribute :>> cost = 44.0;
            attribute range : Real = 144.0;
            port data : Common::DataPort;
        }
        part def Controller_0594 :> Common::Component {
            attribute :>> mass = 1.60 [kg];
            attribute :>> cost = 294.0;
            port supply : Common::PowerPort;
            part sensors : Sensor_0594[2];
            action smooth : Common::Process;
            action forward : Common::Process;
            succession first smooth then forward;
            exhibit state lifecycle : Common::Lifecycle;
        }
        requirement controllerMass_0594 : Common::MassLimit {
            subject component : Controller_0594;
            attribute :>> limit = 2.0 [kg];
        }
    }

    package Subsystem_0595 {
        part def Sensor_0595 :> Common::Component {
            attribute :>> mass = 0.20 [kg];
            attribute :>> cost = 45.0;
            attribute range : Real = 145.0;
            port data : Common::DataPort;
        }
        part def Controller_0595 :> Common::Component {
            attribute :>> mass = 1.00 [kg];
            attribute :>> cost = 295.0;
            port supply : Common::PowerPort;
            part sensors : Sensor_0595[2];
            action smooth : Common::Process;
            action forward : Common::Process;
            succession first smooth then forward;
            exhibit state lifecycle : Common::Lifecycle;
        }
        requirement controllerMass_0595 : Common::MassLimit {
            subject component : Controller_0595;
            attribute :>> limit = 2.0 [kg];
        }
    }

    package Subsystem_0596 {
        part def Sensor_0596 :> Common::Component {
            attribute :>> mass = 0.21 [kg];
            attribute :>> cost = 46.0;
            attribute range : Real = 146.0;
            port data : Common::DataPort;
        }
        part def Controller_0596 :> Common::Component {
            attribute :>> mass = 1.10 [kg];
            attribute :>> cost = 296.0;
            port supply : Common::PowerPort;
            part sensors : Sensor_0596[2];
            action smooth : Common::Process;
            action forward : Common::Process;
            succession first smooth then forward;
            exhibit state lifecycle : Common::Lifecycle;
        }
        requirement controllerMass_0596 : Common::MassLimit {
            subject component : Controller_0596;
            attribute :>> limit = 2.0 [kg];
        }
    }

    package Subsystem_0597 {
        part def Sensor_0597 :> Common::Component {
            attribute :>> mass = 0.22 [kg];
            attribute :>> cost = 47.0;
            attribute range : Real = 147.0;
            port data : Common::DataPort;
        }
        part def Controller_0597 :> Common::Component {
            attribute :>> mass = 1.20 [kg];
            attribute :>> cost = 297.0;
            port supply : Common::PowerPort;
            part sensors : Sensor_0597[2];
            action smooth : Common::Process;
            action forward : Common::Process;
            succession first smooth then forward;
            exhibit state lifecycle : Common::Lifecycle;
        }
        requirement controllerMass_0597 : Common::MassLimit {
            subject component : Controller_0597;
            attribute :>> limit = 2.0 [kg];
        }
    }

    package Subsystem_0598 {
        part def Sensor_0598 :> Common::Component {
            attribute :>> mass = 0.23 [kg];
            attribute :>> cost = 48.0;
            attribute range : Real = 148.0;
            port data : Common::DataPort;
        }
        part def Controller_0598 :> Common::Component {
            attribute :>> mass = 1.30 [kg];
            attribute :>> cost = 298.0;
            port supply : Common::PowerPort;
            part sensors : Sensor_0598[2];
            action smooth : Common::Process;
            action forward : Common::Process;
            succession first smooth then forward;
            exhibit state lifecycle : Common::Lifecycle;
        }
        requirement controllerMass_0598 : Common::MassLimit {
            subject component : Controller_0598;
            attribute :>> limit = 2.0 [kg];
        }
    }

    package Subsystem_0599 {
        part def Sensor_0599 :> Common::Component {
            attribute :>> mass = 0.24 [kg];
            attribute :>> cost = 49.0;
            attribute range : Real = 149.0;
            port data : Common::DataPort;
        }
        part def Controller_0599 :> Common::Component {
            attribute :>> mass = 1.40 [kg];
            attribute :>> cost = 299.0;
            port supply : Common::PowerPort;
            part sensors : Sensor_0599[2];
            action smooth : Common::Process;
            action forward : Common::Process;
            succession first smooth then forward;
            exhibit state lifecycle : Common::Lifecycle;
        }
        requirement controllerMass_0599 : Common::MassLimit {
            subject component : Controller_0599;
            attribute :>> limit = 2.0 [kg];
        }
    }

    package Subsystem_0600 {
        part def Sensor_0600 :> Common::Component {
            attribute :>> mass = 0.20 [kg];
            attribute :>> cost = 30.0;
            attribute range : Real = 100.0;
            port data : Common::DataPort;
        }
        part def Controller_0600 :> Common::Component {
            attribute :>> mass = 1.50 [kg];
            attribute :>> cost = 200.0;
            port supply : Common::PowerPort;
            part sensors : Sensor_0600[2];
            action smooth : Common::Process;
            action forward : Common::Process;
            succession first smooth then forward;
            exhibit state lifecycle : Common::Lifecycle;
        }
        requirement controllerMass_0600 : Common::MassLimit {
            subject component : Controller_0600;
            attribute :>> limit = 2.0 [kg];
        }
    }

    package Subsystem_0601 {
        part def Sensor_0601 :> Common::Component {
            attribute :>> mass = 0.21 [kg];
            attribute :>> cost = 31.0;
            attribute range : Real = 101.0;
            port data : Common::DataPort;
        }
        part def Controller_0601 :> Common::Component {
            attribute :>> mass = 1.60 [kg];
            attribute :>> cost = 201.0;
            port supply : Common::PowerPort;
            part sensors : Sensor_0601[2];
            action smooth : Common::Process;
            action forward : Common::Process;
            succession first smooth then forward;
            exhibit state lifecycle : Common::Lifecycle;
        }
        requirement controllerMass_0601 : Common::MassLimit {
            subject component : Controller_0601;
            attribute :>> limit = 2.0 [kg];
        }
    }

    package Subsystem_0602 {
        part def Sensor_0602 :> Common::Component {
            attribute :>> mass = 0.22 [kg];
            attribute :>> cost = 32.0;
            attribute range : Real = 102.0;
            port data : Common::DataPort;
        }
        part def Controller_0602 :> Common::Component {
            attribute :>> mass = 1.00 [kg];
            attribute :>> cost = 202.0;
            port supply : Common::PowerPort;
            part sensors : Sensor_0602[2];
            action smooth : Common::Process;
            action forward : Common::Process;
            succession first smooth then forward;
            exhibit state lifecycle : Common::Lifecycle;
        }
        requirement controllerMass_0602 : Common::MassLimit {
            subject component : Controller_0602;
            attribute :>> limit = 2.0 [kg];
        }
    }

    package Subsystem_0603 {
        part def Sensor_0603 :> Common::Component {
            attribute :>> mass = 0.23 [kg];
            attribute :>> cost = 33.0;
            attribute range : Real = 103.0;
            port data : Common::DataPort;
        }
        part def Controller_0603 :> Common::Component {
            attribute :>> mass = 1.10 [kg];
            attribute :>> cost = 203.0;
            port supply : Common::PowerPort;
            part sensors : Sensor_0603[2];
            action smooth : Common::Process;
            action forward : Common::Process;
            succession first smooth then forward;
            exhibit state lifecycle : Common::Lifecycle;
        }
        requirement controllerMass_0603 : Common::MassLimit {
            subject component : Controller_0603;
            attribute :>> limit = 2.0 [kg];
        }
    }

    package Subsystem_0604 {
        part def Sensor_0604 :> Common::Component {
            attribute :>> mass = 0.24 [kg];
            attribute :>> cost = 34.0;
            attribute range : Real = 104.0;
            port data : Common::DataPort;
        }
        part def Controller_0604 :> Common::Component {
            attribute :>> mass = 1.20 [kg];
            attribute :>> cost = 204.0;
            port supply : Common::PowerPort;
            part sensors : Sensor_0604[2];
            action smooth : Common::Process;
            action forward : Common::Process;
            succession first smooth then forward;
            exhibit state lifecycle : Common::Lifecycle;
        }
        requirement controllerMass_0604 : Common::MassLimit {
            subject component : Controller_0604;
            attribute :>> limit = 2.0 [kg];
        }
    }

    package Subsystem_0605 {
        part def Sensor_0605 :> Common::Component {
            attribute :>> mass = 0.20 [kg];
            attribute :>> cost = 35.0;
            attribute range : Real = 105.0;
            port data : Common::DataPort;
        }
        part def Controller_0605 :> Common::Component {
            attribute :>> mass = 1.30 [kg];
            attribute :>> cost = 205.0;
            port supply : Common::PowerPort;
            part sensors : Sensor_0605[2];
            action smooth : Common::Process;
            action forward : Common::Process;
            succession first smooth then forward;
            exhibit state lifecycle : Common::Lifecycle;
        }
        requirement controllerMass_0605 : Common::MassLimit {
            subject component : Controller_0605;
            attribute :>> limit = 2.0 [kg];
        }
    }

    package Subsystem_0606 {
        part def Sensor_0606 :> Common::Component {
            attribute :>> mass = 0.21 [kg];
            attribute :>> cost = 36.0;
            attribute range : Real = 106.0;
            port data : Common::DataPort;
        }
        part def Controller_0606 :> Common::Component {
            attribute :>> mass = 1.40 [kg];
            attribute :>> cost = 206.0;
            port supply : Common::PowerPort;
            part sensors : Sensor_0606[2];
            action smooth : Common::Process;
            action forward : Common::Process;
            succession first smooth then forward;
            exhibit state lifecycle : Common::Lifecycle;
        }
        requirement controllerMass_0606 : Common::MassLimit {
            subject component : Controller_0606;
            attribute :>> limit = 2.0 [kg];
        }
    }

    package Subsystem_0607 {
        part def Sensor_0607 :> Common::Component {
            attribute :>> mass = 0.22 [kg];
            attribute :>> cost = 37.0;
            attribute range : Real = 107.0;
            port data : Common::DataPort;
        }
        part def Controller_0607 :> Common::Component {
            attribute :>> mass = 1.50 [kg];
            attribute :>> cost = 207.0;
            port supply : Common::PowerPort;
            part sensors : Sensor_0607[2];
            action smooth : Common::Process;
            action forward : Common::Process;
            succession first smooth then forward;
            exhibit state lifecycle : Common::Lifecycle;
        }
        requirement controllerMass_0607 : Common::MassLimit {
            subject component : Controller_0607;
            attribute :>> limit = 2.0 [kg];
        }
    }

    package Subsystem_0608 {
        part def Sensor_0608 :> Common::Component {
            attribute :>> mass = 0.23 [kg];
            attribute :>> cost = 38.0;
            attribute range : Real = 108.0;
            port data : Common::DataPort;
        }
        part def Controller_0608 :> Common::Component {
            attribute :>> mass = 1.60 [kg];
            attribute :>> cost = 208.0;
            port supply : Common::PowerPort;
            part sensors : Sensor_0608[2];
            action smooth : Common::Process;
            action forward : Common::Process;
            succession first smooth then forward;
            exhibit state lifecycle : Common::Lifecycle;
        }
        requirement controllerMass_0608 : Common::MassLimit {
            subject component : Controller_0608;
            attribute :>> limit = 2.0 [kg];
        }
    }

    package Subsystem_0609 {
        part def Sensor_0609 :> Common::Component {
            attribute :>> mass = 0.24 [kg];
            attribute :>> cost = 39.0;
            attribute range : Real = 109.0;
            port data : Common::DataPort;
        }
        part def Controller_0609 :> Common::Component {
            attribute :>> mass = 1.00 [kg];
            attribute :>> cost = 209.0;
            port supply : Common::PowerPort;
            part sensors : Sensor_0609[2];
            action smooth : Common::Process;
            action forward : Common::Process;
            succession first smooth then forward;
            exhibit state lifecycle : Common::Lifecycle;
        }
        requirement controllerMass_0609 : Common::MassLimit {
            subject component : Controller_0609;
            attribute :>> limit = 2.0 [kg];
        }
    }

    package Subsystem_0610 {
        part def Sensor_0610 :> Common::Component {
            attribute :>> mass = 0.20 [kg];
            attribute :>> cost = 40.0;
            attribute range : Real = 110.0;
            port data : Common::DataPort;
        }
        part def Controller_0610 :> Common::Component {
            attribute :>> mass = 1.10 [kg];
            attribute :>> cost = 210.0;
            port supply : Common::PowerPort;
            part sensors : Sensor_0610[2];
            action smooth : Common::Process;
            action forward : Common::Process;
            succession first smooth then forward;
            exhibit state lifecycle : Common::Lifecycle;
        }
        requirement controllerMass_0610 : Common::MassLimit {
            subject component : Controller_0610;
            attribute :>> limit = 2.0 [kg];
        }
    }

    package Subsystem_0611 {
        part def Sensor_0611 :> Common::Component {
            attribute :>> mass = 0.21 [kg];
            attribute :>> cost = 41.0;
            attribute range : Real = 111.0;
            port data : Common::DataPort;
        }
        part def Controller_0611 :> Common::Component {
            attribute :>> mass = 1.20 [kg];
            attribute :>> cost = 211.0;
            port supply : Common::PowerPort;
            part sensors : Sensor_0611[2];
            action smooth : Common::Process;
            action forward : Common::Process;
            succession first smooth then forward;
            exhibit state lifecycle : Common::Lifecycle;
        }
        requirement controllerMass_0611 : Common::MassLimit {
            subject component : Controller_0611;
            attribute :>> limit = 2.0 [kg];
        }
    }

    package Subsystem_0612 {
        part def Sensor_0612 :> Common::Component {
            attribute :>> mass = 0.22 [kg];
            attribute :>> cost = 42.0;
            attribute range : Real = 112.0;
            port data : Common::DataPort;
        }
        part def Controller_0612 :> Common::Component {
            attribute :>> mass = 1.30 [kg];
            attribute :>> cost = 212.0;
            port supply : Common::PowerPort;
            part sensors : Sensor_0612[2];
            action smooth : Common::Process;
            action forward : Common::Process;
            succession first smooth then forward;
            exhibit state lifecycle : Common::Lifecycle;
        }
        requirement controllerMass_0612 : Common::MassLimit {
            subject component : Controller_0612;
            attribute :>> limit = 2.0 [kg];
        }
    }

    package Subsystem_0613 {
        part def Sensor_0613 :> Common::Component {
            attribute :>> mass = 0.23 [kg];
            attribute :>> cost = 43.0;
            attribute range : Real = 113.0;
            port data : Common::DataPort;
        }
        part def Controller_0613 :> Common::Component {
            attribute :>> mass = 1.40 [kg];
            attribute :>> cost = 213.0;
            port supply : Common::PowerPort;
            part sensors : Sensor_0613[2];
            action smooth : Common::Process;
            action forward : Common::Process;
            succession first smooth then forward;
            exhibit state lifecycle : Common::Lifecycle;
        }
        requirement controllerMass_0613 : Common::MassLimit {
            subject component : Controller_0613;
            attribute :>> limit = 2.0 [kg];
        }
    }

    package Subsystem_0614 {
        part def Sensor_0614 :> Common::Component {
            attribute :>> mass = 0.24 [kg];
            attribute :>> cost = 44.0;
            attribute range : Real = 114.0;
            port data : Common::DataPort;
        }
        part def Controller_0614 :> Common::Component {
            attribute :>> mass = 1.50 [kg];
            attribute :>> cost = 214.0;
            port supply : Common::PowerPort;
            part sensors : Sensor_0614[2];
            action smooth : Common::Process;
            action forward : Common::Process;
            succession first smooth then forward;
            exhibit state lifecycle : Common::Lifecycle;
        }
        requirement controllerMass_0614 : Common::MassLimit {
            subject component : Controller_0614;
            attribute :>> limit = 2.0 [kg];
        }
    }

    package Subsystem_0615 {
        part def Sensor_0615 :> Common::Component {
            attribute :>> mass = 0.20 [kg];
            attribute :>> cost = 45.0;
            attribute range : Real = 115.0;
            port data : Common::DataPort;
        }
        part def Controller_0615 :> Common::Component {
            attribute :>> mass = 1.60 [kg];
            attribute :>> cost = 215.0;
            port supply : Common::PowerPort;
            part sensors : Sensor_0615[2];
            action smooth : Common::Process;
            action forward : Common::Process;
            succession first smooth then forward;
            exhibit state lifecycle : Common::Lifecycle;
        }
        requirement controllerMass_0615 : Common::MassLimit {
            subject component : Controller_0615;
            attribute :>> limit = 2.0 [kg];
        }
    }

    package Subsystem_0616 {
        part def Sensor_0616 :> Common::Component {
            attribute :>> mass = 0.21 [kg];
            attribute :>> cost = 46.0;
            attribute range : Real = 116.0;
            port data : Common::DataPort;
        }
        part def Controller_0616 :> Common::Component {
            attribute :>> mass = 1.00 [kg];
            attribute :>> cost = 216.0;
            port supply : Common::PowerPort;
            part sensors : Sensor_0616[2];
            action smooth : Common::Process;
            action forward : Common::Process;
            succession first smooth then forward;
            exhibit state lifecycle : Common::Lifecycle;
        }
        requirement controllerMass_0616 : Common::MassLimit {
            subject component : Controller_0616;
            attribute :>> limit = 2.0 [kg];
        }
    }

    package Subsystem_0617 {
        part def Sensor_0617 :> Common::Component {
            attribute :>> mass = 0.22 [kg];
            attribute :>> cost = 47.0;
            attribute range : Real = 117.0;
            port data : Common::DataPort;
        }
        part def Controller_0617 :> Common::Component {
            attribute :>> mass = 1.10 [kg];
            attribute :>> cost = 217.0;
            port supply : Common::PowerPort;
            part sensors : Sensor_0617[2];
            action smooth : Common::Process;
            action forward : Common::Process;
            succession first smooth then forward;
            exhibit state lifecycle : Common::Lifecycle;
        }
        requirement controllerMass_0617 : Common::MassLimit {
            subject component : Controller_0617;
            attribute :>> limit = 2.0 [kg];
        }
    }

    package Subsystem_0618 {
        part def Sensor_0618 :> Common::Component {
            attribute :>> mass = 0.23 [kg];
            attribute :>> cost = 48.0;
            attribute range : Real = 118.0;
            port data : Common::DataPort;
        }
        part def Controller_0618 :> Common::Component {
            attribute :>> mass = 1.20 [kg];
            attribute :>> cost = 218.0;
            port supply : Common::PowerPort;
            part sensors : Sensor_0618[2];
            action smooth : Common::Process;
            action forward : Common::Process;
            succession first smooth then forward;
            exhibit state lifecycle : Common::Lifecycle;
        }
        requirement controllerMass_0618 : Common::MassLimit {
            subject component : Controller_0618;
            attribute :>> limit = 2.0 [kg];
        }
    }

    package Subsystem_0619 {
        part def Sensor_0619 :> Common::Component {
            attribute :>> mass = 0.24 [kg];
            attribute :>> cost = 49.0;
            attribute range : Real = 119.0;
            port data : Common::DataPort;
        }
        part def Controller_0619 :> Common::Component {
            attribute :>> mass = 1.30 [kg];
            attribute :>> cost = 219.0;
            port supply : Common::PowerPort;
            part sensors : Sensor_0619[2];
            action smooth : Common::Process;
            action forward : Common::Process;
            succession first smooth then forward;
            exhibit state lifecycle : Common::Lifecycle;
        }
        requirement controllerMass_0619 : Common::MassLimit {
            subject component : Controller_0619;
            attribute :>> limit = 2.0 [kg];
        }
    }

    package Subsystem_0620 {
        part def Sensor_0620 :> Common::Component {
            attribute :>> mass = 0.20 [kg];
            attribute :>> cost = 30.0;
            attribute range : Real = 120.0;
            port data : Common::DataPort;
        }
        part def Controller_0620 :> Common::Component {
            attribute :>> mass = 1.40 [kg];
            attribute :>> cost = 220.0;
            port supply : Common::PowerPort;
            part sensors : Sensor_0620[2];
            action smooth : Common::Process;
            action forward : Common::Process;
            succession first smooth then forward;
            exhibit state lifecycle : Common::Lifecycle;
        }
        requirement controllerMass_0620 : Common::MassLimit {
            subject component : Controller_0620;
            attribute :>> limit = 2.0 [kg];
        }
    }

    package Subsystem_0621 {
        part def Sensor_0621 :> Common::Component {
            attribute :>> mass = 0.21 [kg];
            attribute :>> cost = 31.0;
            attribute range : Real = 121.0;
            port data : Common::DataPort;
        }
        part def Controller_0621 :> Common::Component {
            attribute :>> mass = 1.50 [kg];
            attribute :>> cost = 221.0;
            port supply : Common::PowerPort;
            part sensors : Sensor_0621[2];
            action smooth : Common::Process;
            action forward : Common::Process;
            succession first smooth then forward;
            exhibit state lifecycle : Common::Lifecycle;
        }
        requirement controllerMass_0621 : Common::MassLimit {
            subject component : Controller_0621;
            attribute :>> limit = 2.0 [kg];
        }
    }

    package Subsystem_0622 {
        part def Sensor_0622 :> Common::Component {
            attribute :>> mass = 0.22 [kg];
            attribute :>> cost = 32.0;
            attribute range : Real = 122.0;
            port data : Common::DataPort;
        }
        part def Controller_0622 :> Common::Component {
            attribute :>> mass = 1.60 [kg];
            attribute :>> cost = 222.0;
            port supply : Common::PowerPort;
            part sensors : Sensor_0622[2];
            action smooth : Common::Process;
            action forward : Common::Process;
            succession first smooth then forward;
            exhibit state lifecycle : Common::Lifecycle;
        }
        requirement controllerMass_0622 : Common::MassLimit {
            subject component : Controller_0622;
            attribute :>> limit = 2.0 [kg];
        }
    }

    package Subsystem_0623 {
        part def Sensor_0623 :> Common::Component {
            attribute :>> mass = 0.23 [kg];
            attribute :>> cost = 33.0;
            attribute range : Real = 123.0;
            port data : Common::DataPort;
        }
        part def Controller_0623 :> Common::Component {
            attribute :>> mass = 1.00 [kg];
            attribute :>> cost = 223.0;
            port supply : Common::PowerPort;
            part sensors : Sensor_0623[2];
            action smooth : Common::Process;
            action forward : Common::Process;
            succession first smooth then forward;
            exhibit state lifecycle : Common::Lifecycle;
        }
        requirement controllerMass_0623 : Common::MassLimit {
            subject component : Controller_0623;
            attribute :>> limit = 2.0 [kg];
        }
    }

    package Subsystem_0624 {
        part def Sensor_0624 :> Common::Component {
            attribute :>> mass = 0.24 [kg];
            attribute :>> cost = 34.0;
            attribute range : Real = 124.0;
            port data : Common::DataPort;
        }
        part def Controller_0624 :> Common::Component {
            attribute :>> mass = 1.10 [kg];
            attribute :>> cost = 224.0;
            port supply : Common::PowerPort;
            part sensors : Sensor_0624[2];
            action smooth : Common::Process;
            action forward : Common::Process;
            succession first smooth then forward;
            exhibit state lifecycle : Common::Lifecycle;
        }
        requirement controllerMass_0624 : Common::MassLimit {
            subject component : Controller_0624;
            attribute :>> limit = 2.0 [kg];
        }
    }

    package Subsystem_0625 {
        part def Sensor_0625 :> Common::Component {
            attribute :>> mass = 0.20 [kg];
            attribute :>> cost = 35.0;
            attribute range : Real = 125.0;
            port data : Common::DataPort;
        }
        part def Controller_0625 :> Common::Component {
            attribute :>> mass = 1.20 [kg];
            attribute :>> cost = 225.0;
            port supply : Common::PowerPort;
            part sensors : Sensor_0625[2];
            action smooth : Common::Process;
            action forward : Common::Process;
            succession first smooth then forward;
            exhibit state lifecycle : Common::Lifecycle;
        }
        requirement controllerMass_0625 : Common::MassLimit {
            subject component : Controller_0625;
            attribute :>> limit = 2.0 [kg];
        }
    }

    package Subsystem_0626 {
        part def Sensor_0626 :> Common::Component {
            attribute :>> mass = 0.21 [kg];
            attribute :>> cost = 36.0;
            attribute range : Real = 126.0;
            port data : Common::DataPort;
        }
        part def Controller_0626 :> Common::Component {
            attribute :>> mass = 1.30 [kg];
            attribute :>> cost = 226.0;
            port supply : Common::PowerPort;
            part sensors : Sensor_0626[2];
            action smooth : Common::Process;
            action forward : Common::Process;
            succession first smooth then forward;
            exhibit state lifecycle : Common::Lifecycle;
        }
        requirement controllerMass_0626 : Common::MassLimit {
            subject component : Controller_0626;
            attribute :>> limit = 2.0 [kg];
        }
    }

    package Subsystem_0627 {
        part def Sensor_0627 :> Common::Component {
            attribute :>> mass = 0.22 [kg];
            attribute :>> cost = 37.0;
            attribute range : Real = 127.0;
            port data : Common::DataPort;
        }
        part def Controller_0627 :> Common::Component {
            attribute :>> mass = 1.40 [kg];
            attribute :>> cost = 227.0;
            port supply : Common::PowerPort;
            part sensors : Sensor_0627[2];
            action smooth : Common::Process;
            action forward : Common::Process;
            succession first smooth then forward;
            exhibit state lifecycle : Common::Lifecycle;
        }
        requirement controllerMass_0627 : Common::MassLimit {
            subject component : Controller_0627;
            attribute :>> limit = 2.0 [kg];
        }
    }

    package Subsystem_0628 {
        part def Sensor_0628 :> Common::Component {
            attribute :>> mass = 0.23 [kg];
            attribute :>> cost = 38.0;
            attribute range : Real = 128.0;
            port data : Common::DataPort;
        }
        part def Controller_0628 :> Common::Component {
            attribute :>> mass = 1.50 [kg];
            attribute :>> cost = 228.0;
            port supply : Common::PowerPort;
            part sensors : Sensor_0628[2];
            action smooth : Common::Process;
            action forward : Common::Process;
            succession first smooth then forward;
            exhibit state lifecycle : Common::Lifecycle;
        }
        requirement controllerMass_0628 : Common::MassLimit {
            subject component : Controller_0628;
            attribute :>> limit = 2.0 [kg];
        }
    }

    package Subsystem_0629 {
        part def Sensor_0629 :> Common::Component {
            attribute :>> mass = 0.24 [kg];
            attribute :>> cost = 39.0;
            attribute range : Real = 129.0;
            port data : Common::DataPort;
        }
        part def Controller_0629 :> Common::Component {
            attribute :>> mass = 1.60 [kg];
            attribute :>> cost = 229.0;
            port supply : Common::PowerPort;
            part sensors : Sensor_0629[2];
            action smooth : Common::Process;
            action forward : Common::Process;
            succession first smooth then forward;
            exhibit state lifecycle : Common::Lifecycle;
        }
        requirement controllerMass_0629 : Common::MassLimit {
            subject component : Controller_0629;
            attribute :>> limit = 2.0 [kg];
        }
    }

    package Subsystem_0630 {
        part def Sensor_0630 :> Common::Component {
            attribute :>> mass = 0.20 [kg];
            attribute :>> cost = 40.0;
            attribute range : Real = 130.0;
            port data : Common::DataPort;
        }
        part def Controller_0630 :> Common::Component {
            attribute :>> mass = 1.00 [kg];
            attribute :>> cost = 230.0;
            port supply : Common::PowerPort;
            part sensors : Sensor_0630[2];
            action smooth : Common::Process;
            action forward : Common::Process;
            succession first smooth then forward;
            exhibit state lifecycle : Common::Lifecycle;
        }
        requirement controllerMass_0630 : Common::MassLimit {
            subject component : Controller_0630;
            attribute :>> limit = 2.0 [kg];
        }
    }

    package Subsystem_0631 {
        part def Sensor_0631 :> Common::Component {
            attribute :>> mass = 0.21 [kg];
            attribute :>> cost = 41.0;
            attribute range : Real = 131.0;
            port data : Common::DataPort;
        }
        part def Controller_0631 :> Common::Component {
            attribute :>> mass = 1.10 [kg];
            attribute :>> cost = 231.0;
            port supply : Common::PowerPort;
            part sensors : Sensor_0631[2];
            action smooth : Common::Process;
            action forward : Common::Process;
            succession first smooth then forward;
            exhibit state lifecycle : Common::Lifecycle;
        }
        requirement controllerMass_0631 : Common::MassLimit {
            subject component : Controller_0631;
            attribute :>> limit = 2.0 [kg];
        }
    }

    package Subsystem_0632 {
        part def Sensor_0632 :> Common::Component {
            attribute :>> mass = 0.22 [kg];
            attribute :>> cost = 42.0;
            attribute range : Real = 132.0;
            port data : Common::DataPort;
        }
        part def Controller_0632 :> Common::Component {
            attribute :>> mass = 1.20 [kg];
            attribute :>> cost = 232.0;
            port supply : Common::PowerPort;
            part sensors : Sensor_0632[2];
            action smooth : Common::Process;
            action forward : Common::Process;
            succession first smooth then forward;
            exhibit state lifecycle : Common::Lifecycle;
        }
        requirement controllerMass_0632 : Common::MassLimit {
            subject component : Controller_0632;
            attribute :>> limit = 2.0 [kg];
        }
    }

    package Subsystem_0633 {
        part def Sensor_0633 :> Common::Component {
            attribute :>> mass = 0.23 [kg];
            attribute :>> cost = 43.0;
            attribute range : Real = 133.0;
            port data : Common::DataPort;
        }
        part def Controller_0633 :> Common::Component {
            attribute :>> mass = 1.30 [kg];
            attribute :>> cost = 233.0;
            port supply : Common::PowerPort;
            part sensors : Sensor_0633[2];
            action smooth : Common::Process;
            action forward : Common::Process;
            succession first smooth then forward;
            exhibit state lifecycle : Common::Lifecycle;
        }
        requirement controllerMass_0633 : Common::MassLimit {
            subject component : Controller_0633;
            attribute :>> limit = 2.0 [kg];
        }
    }

    package Subsystem_0634 {
        part def Sensor_0634 :> Common::Component {
            attribute :>> mass = 0.24 [kg];
            attribute :>> cost = 44.0;
            attribute range : Real = 134.0;
            port data : Common::DataPort;
        }
        part def Controller_0634 :> Common::Component {
            attribute :>> mass = 1.40 [kg];
            attribute :>> cost = 234.0;
            port supply : Common::PowerPort;
            part sensors : Sensor_0634[2];
            action smooth : Common::Process;
            action forward : Common::Process;
            succession first smooth then forward;
            exhibit state lifecycle : Common::Lifecycle;
        }
        requirement controllerMass_0634 : Common::MassLimit {
            subject component : Controller_0634;
            attribute :>> limit = 2.0 [kg];
        }
    }

    package Subsystem_0635 {
        part def Sensor_0635 :> Common::Component {
            attribute :>> mass = 0.20 [kg];
            attribute :>> cost = 45.0;
            attribute range : Real = 135.0;
            port data : Common::DataPort;
        }
        part def Controller_0635 :> Common::Component {
            attribute :>> mass = 1.50 [kg];
            attribute :>> cost = 235.0;
            port supply : Common::PowerPort;
            part sensors : Sensor_0635[2];
            action smooth : Common::Process;
            action forward : Common::Process;
            succession first smooth then forward;
            exhibit state lifecycle : Common::Lifecycle;
        }
        requirement controllerMass_0635 : Common::MassLimit {
            subject component : Controller_0635;
            attribute :>> limit = 2.0 [kg];
        }
    }

    package Subsystem_0636 {
        part def Sensor_0636 :> Common::Component {
            attribute :>> mass = 0.21 [kg];
            attribute :>> cost = 46.0;
            attribute range : Real = 136.0;
            port data : Common::DataPort;
        }
        part def Controller_0636 :> Common::Component {
            attribute :>> mass = 1.60 [kg];
            attribute :>> cost = 236.0;
            port supply : Common::PowerPort;
            part sensors : Sensor_0636[2];
            action smooth : Common::Process;
            action forward : Common::Process;
            succession first smooth then forward;
            exhibit state lifecycle : Common::Lifecycle;
        }
        requirement controllerMass_0636 : Common::MassLimit {
            subject component : Controller_0636;
            attribute :>> limit = 2.0 [kg];
        }
    }

    package Subsystem_0637 {
        part def Sensor_0637 :> Common::Component {
            attribute :>> mass = 0.22 [kg];
            attribute :>> cost = 47.0;
            attribute range : Real = 137.0;
            port data : Common::DataPort;
        }
        part def Controller_0637 :> Common::Component {
            attribute :>> mass = 1.00 [kg];
            attribute :>> cost = 237.0;
            port supply : Common::PowerPort;
            part sensors : Sensor_0637[2];
            action smooth : Common::Process;
            action forward : Common::Process;
            succession first smooth then forward;
            exhibit state lifecycle : Common::Lifecycle;
        }
        requirement controllerMass_0637 : Common::MassLimit {
            subject component : Controller_0637;
            attribute :>> limit = 2.0 [kg];
        }
    }

    package Subsystem_0638 {
        part def Sensor_0638 :> Common::Component {
            attribute :>> mass = 0.23 [kg];
            attribute :>> cost = 48.0;
            attribute range : Real = 138.0;
            port data : Common::DataPort;
        }
        part def Controller_0638 :> Common::Component {
            attribute :>> mass = 1.10 [kg];
            attribute :>> cost = 238.0;
            port supply : Common::PowerPort;
            part sensors : Sensor_0638[2];
            action smooth : Common::Process;
            action forward : Common::Process;
            succession first smooth then forward;
            exhibit state lifecycle : Common::Lifecycle;
        }
        requirement controllerMass_0638 : Common::MassLimit {
            subject component : Controller_0638;
            attribute :>> limit = 2.0 [kg];
        }
    }

    package Subsystem_0639 {
        part def Sensor_0639 :> Common::Component {
            attribute :>> mass = 0.24 [kg];
            attribute :>> cost = 49.0;
            attribute range : Real = 139.0;
            port data : Common::DataPort;
        }
        part def Controller_0639 :> Common::Component {
            attribute :>> mass = 1.20 [kg];
            attribute :>> cost = 239.0;
            port supply : Common::PowerPort;
            part sensors : Sensor_0639[2];
            action smooth : Common::Process;
            action forward : Common::Process;
            succession first smooth then forward;
            exhibit state lifecycle : Common::Lifecycle;
        }
        requirement controllerMass_0639 : Common::MassLimit {
            subject component : Controller_0639;
            attribute :>> limit = 2.0 [kg];
        }
    }

    package Subsystem_0640 {
        part def Sensor_0640 :> Common::Component {
            attribute :>> mass = 0.20 [kg];
            attribute :>> cost = 30.0;
            attribute range : Real = 140.0;
            port data : Common::DataPort;
        }
        part def Controller_0640 :> Common::Component {
            attribute :>> mass = 1.30 [kg];
            attribute :>> cost = 240.0;
            port supply : Common::PowerPort;
            part sensors : Sensor_0640[2];
            action smooth : Common::Process;
            action forward : Common::Process;
            succession first smooth then forward;
            exhibit state lifecycle : Common::Lifecycle;
        }
        requirement controllerMass_0640 : Common::MassLimit {
            subject component : Controller_0640;
            attribute :>> limit = 2.0 [kg];
        }
    }

    package Subsystem_0641 {
        part def Sensor_0641 :> Common::Component {
            attribute :>> mass = 0.21 [kg];
            attribute :>> cost = 31.0;
            attribute range : Real = 141.0;
            port data : Common::DataPort;
        }
        part def Controller_0641 :> Common::Component {
            attribute :>> mass = 1.40 [kg];
            attribute :>> cost = 241.0;
            port supply : Common::PowerPort;
            part sensors : Sensor_0641[2];
            action smooth : Common::Process;
            action forward : Common::Process;
            succession first smooth then forward;
            exhibit state lifecycle : Common::Lifecycle;
        }
        requirement controllerMass_0641 : Common::MassLimit {
            subject component : Controller_0641;
            attribute :>> limit = 2.0 [kg];
        }
    }

    package Subsystem_0642 {
        part def Sensor_0642 :> Common::Component {
            attribute :>> mass = 0.22 [kg];
            attribute :>> cost = 32.0;
            attribute range : Real = 142.0;
            port data : Common::DataPort;
        }
        part def Controller_0642 :> Common::Component {
            attribute :>> mass = 1.50 [kg];
            attribute :>> cost = 242.0;
            port supply : Common::PowerPort;
            part sensors : Sensor_0642[2];
            action smooth : Common::Process;
            action forward : Common::Process;
            succession first smooth then forward;
            exhibit state lifecycle : Common::Lifecycle;
        }
        requirement controllerMass_0642 : Common::MassLimit {
            subject component : Controller_0642;
            attribute :>> limit = 2.0 [kg];
        }
    }

    package Subsystem_0643 {
        part def Sensor_0643 :> Common::Component {
            attribute :>> mass = 0.23 [kg];
            attribute :>> cost = 33.0;
            attribute range : Real = 143.0;
            port data : Common::DataPort;
        }
        part def Controller_0643 :> Common::Component {
            attribute :>> mass = 1.60 [kg];
            attribute :>> cost = 243.0;
            port supply : Common::PowerPort;
            part sensors : Sensor_0643[2];
            action smooth : Common::Process;
            action forward : Common::Process;
            succession first smooth then forward;
            exhibit state lifecycle : Common::Lifecycle;
        }
        requirement controllerMass_0643 : Common::MassLimit {
            subject component : Controller_0643;
            attribute :>> limit = 2.0 [kg];
        }
    }

    package Subsystem_0644 {
        part def Sensor_0644 :> Common::Component {
            attribute :>> mass = 0.24 [kg];
            attribute :>> cost = 34.0;
            attribute range : Real = 144.0;
            port data : Common::DataPort;
        }
        part def Controller_0644 :> Common::Component {
            attribute :>> mass = 1.00 [kg];
            attribute :>> cost = 244.0;
            port supply : Common::PowerPort;
            part sensors : Sensor_0644[2];
            action smooth : Common::Process;
            action forward : Common::Process;
            succession first smooth then forward;
            exhibit state lifecycle : Common::Lifecycle;
        }
        requirement controllerMass_0644 : Common::MassLimit {
            subject component : Controller_0644;
            attribute :>> limit = 2.0 [kg];
        }
    }

    package Subsystem_0645 {
        part def Sensor_0645 :> Common::Component {
            attribute :>> mass = 0.20 [kg];
            attribute :>> cost = 35.0;
            attribute range : Real = 145.0;
            port data : Common::DataPort;
        }
        part def Controller_0645 :> Common::Component {
            attribute :>> mass = 1.10 [kg];
            attribute :>> cost = 245.0;
            port supply : Common::PowerPort;
            part sensors : Sensor_0645[2];
            action smooth : Common::Process;
            action forward : Common::Process;
            succession first smooth then forward;
            exhibit state lifecycle : Common::Lifecycle;
        }
        requirement controllerMass_0645 : Common::MassLimit {
            subject component : Controller_0645;
            attribute :>> limit = 2.0 [kg];
        }
    }

    package Subsystem_0646 {
        part def Sensor_0646 :> Common::Component {
            attribute :>> mass = 0.21 [kg];
            attribute :>> cost = 36.0;
            attribute range : Real = 146.0;
            port data : Common::DataPort;
        }
        part def Controller_0646 :> Common::Component {
            attribute :>> mass = 1.20 [kg];
            attribute :>> cost = 246.0;
            port supply : Common::PowerPort;
            part sensors : Sensor_0646[2];
            action smooth : Common::Process;
            action forward : Common::Process;
            succession first smooth then forward;
            exhibit state lifecycle : Common::Lifecycle;
        }
        requirement controllerMass_0646 : Common::MassLimit {
            subject component : Controller_0646;
            attribute :>> limit = 2.0 [kg];
        }
    }

    package Subsystem_0647 {
        part def Sensor_0647 :> Common::Component {
            attribute :>> mass = 0.22 [kg];
            attribute :>> cost = 37.0;
            attribute range : Real = 147.0;
            port data : Common::DataPort;
        }
        part def Controller_0647 :> Common::Component {
            attribute :>> mass = 1.30 [kg];
            attribute :>> cost = 247.0;
            port supply : Common::PowerPort;
            part sensors : Sensor_0647[2];
            action smooth : Common::Process;
            action forward : Common::Process;
            succession first smooth then forward;
            exhibit state lifecycle : Common::Lifecycle;
        }
        requirement controllerMass_0647 : Common::MassLimit {
            subject component : Controller_0647;
            attribute :>> limit = 2.0 [kg];
        }
    }

    package Subsystem_0648 {
        part def Sensor_0648 :> Common::Component {
            attribute :>> mass = 0.23 [kg];
            attribute :>> cost = 38.0;
            attribute range : Real = 148.0;
            port data : Common::DataPort;
        }
        part def Controller_0648 :> Common::Component {
            attribute :>> mass = 1.40 [kg];
            attribute :>> cost = 248.0;
            port supply : Common::PowerPort;
            part sensors : Sensor_0648[2];
            action smooth : Common::Process;
            action forward : Common::Process;
            succession first smooth then forward;
            exhibit state lifecycle : Common::Lifecycle;
        }
        requirement controllerMass_0648 : Common::MassLimit {
            subject component : Controller_0648;
            attribute :>> limit = 2.0 [kg];
        }
    }

    package Subsystem_0649 {
        part def Sensor_0649 :> Common::Component {
            attribute :>> mass = 0.24 [kg];
            attribute :>> cost = 39.0;
            attribute range : Real = 149.0;
            port data : Common::DataPort;
        }
        part def Controller_0649 :> Common::Component {
            attribute :>> mass = 1.50 [kg];
            attribute :>> cost = 249.0;
            port supply : Common::PowerPort;
            part sensors : Sensor_0649[2];
            action smooth : Common::Process;
            action forward : Common::Process;
            succession first smooth then forward;
            exhibit state lifecycle : Common::Lifecycle;
        }
        requirement controllerMass_0649 : Common::MassLimit {
            subject component : Controller_0649;
            attribute :>> limit = 2.0 [kg];
        }
    }

    package Subsystem_0650 {
        part def Sensor_0650 :> Common::Component {
            attribute :>> mass = 0.20 [kg];
            attribute :>> cost = 40.0;
            attribute range : Real = 100.0;
            port data : Common::DataPort;
        }
        part def Controller_0650 :> Common::Component {
            attribute :>> mass = 1.60 [kg];
            attribute :>> cost = 250.0;
            port supply : Common::PowerPort;
            part sensors : Sensor_0650[2];
            action smooth : Common::Process;
            action forward : Common::Process;
            succession first smooth then forward;
            exhibit state lifecycle : Common::Lifecycle;
        }
        requirement controllerMass_0650 : Common::MassLimit {
            subject component : Controller_0650;
            attribute :>> limit = 2.0 [kg];
        }
    }

    package Subsystem_0651 {
        part def Sensor_0651 :> Common::Component {
            attribute :>> mass = 0.21 [kg];
            attribute :>> cost = 41.0;
            attribute range : Real = 101.0;
            port data : Common::DataPort;
        }
        part def Controller_0651 :> Common::Component {
            attribute :>> mass = 1.00 [kg];
            attribute :>> cost = 251.0;
            port supply : Common::PowerPort;
            part sensors : Sensor_0651[2];
            action smooth : Common::Process;
            action forward : Common::Process;
            succession first smooth then forward;
            exhibit state lifecycle : Common::Lifecycle;
        }
        requirement controllerMass_0651 : Common::MassLimit {
            subject component : Controller_0651;
            attribute :>> limit = 2.0 [kg];
        }
    }

    package Subsystem_0652 {
        part def Sensor_0652 :> Common::Component {
            attribute :>> mass = 0.22 [kg];
            attribute :>> cost = 42.0;
            attribute range : Real = 102.0;
            port data : Common::DataPort;
        }
        part def Controller_0652 :> Common::Component {
            attribute :>> mass = 1.10 [kg];
            attribute :>> cost = 252.0;
            port supply : Common::PowerPort;
            part sensors : Sensor_0652[2];
            action smooth : Common::Process;
            action forward : Common::Process;
            succession first smooth then forward;
            exhibit state lifecycle : Common::Lifecycle;
        }
        requirement controllerMass_0652 : Common::MassLimit {
            subject component : Controller_0652;
            attribute :>> limit = 2.0 [kg];
        }
    }

    package Subsystem_0653 {
        part def Sensor_0653 :> Common::Component {
            attribute :>> mass = 0.23 [kg];
            attribute :>> cost = 43.0;
            attribute range : Real = 103.0;
            port data : Common::DataPort;
        }
        part def Controller_0653 :> Common::Component {
            attribute :>> mass = 1.20 [kg];
            attribute :>> cost = 253.0;
            port supply : Common::PowerPort;
            part sensors : Sensor_0653[2];
            action smooth : Common::Process;
            action forward : Common::Process;
            succession first smooth then forward;
            exhibit state lifecycle : Common::Lifecycle;
        }
        requirement controllerMass_0653 : Common::MassLimit {
            subject component : Controller_0653;
            attribute :>> limit = 2.0 [kg];
        }
    }

    package Subsystem_0654 {
        part def Sensor_0654 :> Common::Component {
            attribute :>> mass = 0.24 [kg];
            attribute :>> cost = 44.0;
            attribute range : Real = 104.0;
            port data : Common::DataPort;
        }
        part def Controller_0654 :> Common::Component {
            attribute :>> mass = 1.30 [kg];
            attribute :>> cost = 254.0;
            port supply : Common::PowerPort;
            part sensors : Sensor_0654[2];
            action smooth : Common::Process;
            action forward : Common::Process;
            succession first smooth then forward;
            exhibit state lifecycle : Common::Lifecycle;
        }
        requirement controllerMass_0654 : Common::MassLimit {
            subject component : Controller_0654;
            attribute :>> limit = 2.0 [kg];
        }
    }

    package Subsystem_0655 {
        part def Sensor_0655 :> Common::Component {
            attribute :>> mass = 0.20 [kg];
            attribute :>> cost = 45.0;
            attribute range : Real = 105.0;
            port data : Common::DataPort;
        }
        part def Controller_0655 :> Common::Component {
            attribute :>> mass = 1.40 [kg];
            attribute :>> cost = 255.0;
            port supply : Common::PowerPort;
            part sensors : Sensor_0655[2];
            action smooth : Common::Process;
            action forward : Common::Process;
            succession first smooth then forward;
            exhibit state lifecycle : Common::Lifecycle;
        }
        requirement controllerMass_0655 : Common::MassLimit {
            subject component : Controller_0655;
            attribute :>> limit = 2.0 [kg];
        }
    }

    package Subsystem_0656 {
        part def Sensor_0656 :> Common::Component {
            attribute :>> mass = 0.21 [kg];
            attribute :>> cost = 46.0;
            attribute range : Real = 106.0;
            port data : Common::DataPort;
        }
        part def Controller_0656 :> Common::Component {
            attribute :>> mass = 1.50 [kg];
            attribute :>> cost = 256.0;
            port supply : Common::PowerPort;
            part sensors : Sensor_0656[2];
            action smooth : Common::Process;
            action forward : Common::Process;
            succession first smooth then forward;
            exhibit state lifecycle : Common::Lifecycle;
        }
        requirement controllerMass_0656 : Common::MassLimit {
            subject component : Controller_0656;
            attribute :>> limit = 2.0 [kg];
        }
    }

    package Subsystem_0657 {
        part def Sensor_0657 :> Common::Component {
            attribute :>> mass = 0.22 [kg];
            attribute :>> cost = 47.0;
            attribute range : Real = 107.0;
            port data : Common::DataPort;
        }
        part def Controller_0657 :> Common::Component {
            attribute :>> mass = 1.60 [kg];
            attribute :>> cost = 257.0;
            port supply : Common::PowerPort;
            part sensors : Sensor_0657[2];
            action smooth : Common::Process;
            action forward : Common::Process;
            succession first smooth then forward;
            exhibit state lifecycle : Common::Lifecycle;
        }
        requirement controllerMass_0657 : Common::MassLimit {
            subject component : Controller_0657;
            attribute :>> limit = 2.0 [kg];
        }
    }

    package Subsystem_0658 {
        part def Sensor_0658 :> Common::Component {
            attribute :>> mass = 0.23 [kg];
            attribute :>> cost = 48.0;
            attribute range : Real = 108.0;
            port data : Common::DataPort;
        }
        part def Controller_0658 :> Common::Component {
            attribute :>> mass = 1.00 [kg];
            attribute :>> cost = 258.0;
            port supply : Common::PowerPort;
            part sensors : Sensor_0658[2];
            action smooth : Common::Process;
            action forward : Common::Process;
            succession first smooth then forward;
            exhibit state lifecycle : Common::Lifecycle;
        }
        requirement controllerMass_0658 : Common::MassLimit {
            subject component : Controller_0658;
            attribute :>> limit = 2.0 [kg];
        }
    }

    package Subsystem_0659 {
        part def Sensor_0659 :> Common::Component {
            attribute :>> mass = 0.24 [kg];
            attribute :>> cost = 49.0;
            attribute range : Real = 109.0;
            port data : Common::DataPort;
        }
        part def Controller_0659 :> Common::Component {
            attribute :>> mass = 1.10 [kg];
            attribute :>> cost = 259.0;
            port supply : Common::PowerPort;
            part sensors : Sensor_0659[2];
            action smooth : Common::Process;
            action forward : Common::Process;
            succession first smooth then forward;
            exhibit state lifecycle : Common::Lifecycle;
        }
        requirement controllerMass_0659 : Common::MassLimit {
            subject component : Controller_0659;
            attribute :>> limit = 2.0 [kg];
        }
    }

    package Subsystem_0660 {
        part def Sensor_0660 :> Common::Component {
            attribute :>> mass = 0.20 [kg];
            attribute :>> cost = 30.0;
            attribute range : Real = 110.0;
            port data : Common::DataPort;
        }
        part def Controller_0660 :> Common::Component {
            attribute :>> mass = 1.20 [kg];
            attribute :>> cost = 260.0;
            port supply : Common::PowerPort;
            part sensors : Sensor_0660[2];
            action smooth : Common::Process;
            action forward : Common::Process;
            succession first smooth then forward;
            exhibit state lifecycle : Common::Lifecycle;
        }
        requirement controllerMass_0660 : Common::MassLimit {
            subject component : Controller_0660;
            attribute :>> limit = 2.0 [kg];
        }
    }

    package Subsystem_0661 {
        part def Sensor_0661 :> Common::Component {
            attribute :>> mass = 0.21 [kg];
            attribute :>> cost = 31.0;
            attribute range : Real = 111.0;
            port data : Common::DataPort;
        }
        part def Controller_0661 :> Common::Component {
            attribute :>> mass = 1.30 [kg];
            attribute :>> cost = 261.0;
            port supply : Common::PowerPort;
            part sensors : Sensor_0661[2];
            action smooth : Common::Process;
            action forward : Common::Process;
            succession first smooth then forward;
            exhibit state lifecycle : Common::Lifecycle;
        }
        requirement controllerMass_0661 : Common::MassLimit {
            subject component : Controller_0661;
            attribute :>> limit = 2.0 [kg];
        }
    }

    package Subsystem_0662 {
        part def Sensor_0662 :> Common::Component {
            attribute :>> mass = 0.22 [kg];
            attribute :>> cost = 32.0;
            attribute range : Real = 112.0;
            port data : Common::DataPort;
        }
        part def Controller_0662 :> Common::Component {
            attribute :>> mass = 1.40 [kg];
            attribute :>> cost = 262.0;
            port supply : Common::PowerPort;
            part sensors : Sensor_0662[2];
            action smooth : Common::Process;
            action forward : Common::Process;
            succession first smooth then forward;
            exhibit state lifecycle : Common::Lifecycle;
        }
        requirement controllerMass_0662 : Common::MassLimit {
            subject component : Controller_0662;
            attribute :>> limit = 2.0 [kg];
        }
    }

    package Subsystem_0663 {
        part def Sensor_0663 :> Common::Component {
            attribute :>> mass = 0.23 [kg];
            attribute :>> cost = 33.0;
            attribute range : Real = 113.0;
            port data : Common::DataPort;
        }
        part def Controller_0663 :> Common::Component {
            attribute :>> mass = 1.50 [kg];
            attribute :>> cost = 263.0;
            port supply : Common::PowerPort;
            part sensors : Sensor_0663[2];
            action smooth : Common::Process;
            action forward : Common::Process;
            succession first smooth then forward;
            exhibit state lifecycle : Common::Lifecycle;
        }
        requirement controllerMass_0663 : Common::MassLimit {
            subject component : Controller_0663;
            attribute :>> limit = 2.0 [kg];
        }
    }

    package Subsystem_0664 {
        part def Sensor_0664 :> Common::Component {
            attribute :>> mass = 0.24 [kg];
            attribute :>> cost = 34.0;
            attribute range : Real = 114.0;
            port data : Common::DataPort;
        }
        part def Controller_0664 :> Common::Component {
            attribute :>> mass = 1.60 [kg];
            attribute :>> cost = 264.0;
            port supply : Common::PowerPort;
            part sensors : Sensor_0664[2];
            action smooth : Common::Process;
            action forward : Common::Process;
            succession first smooth then forward;
            exhibit state lifecycle : Common::Lifecycle;
        }
        requirement controllerMass_0664 : Common::MassLimit {
            subject component : Controller_0664;
            attribute :>> limit = 2.0 [kg];
        }
    }

    package Subsystem_0665 {
        part def Sensor_0665 :> Common::Component {
            attribute :>> mass = 0.20 [kg];
            attribute :>> cost = 35.0;
            attribute range : Real = 115.0;
            port data : Common::DataPort;
        }
        part def Controller_0665 :> Common::Component {
            attribute :>> mass = 1.00 [kg];
            attribute :>> cost = 265.0;
            port supply : Common::PowerPort;
            part sensors : Sensor_0665[2];
            action smooth : Common::Process;
            action forward : Common::Process;
            succession first smooth then forward;
            exhibit state lifecycle : Common::Lifecycle;
        }
        requirement controllerMass_0665 : Common::MassLimit {
            subject component : Controller_0665;
            attribute :>> limit = 2.0 [kg];
        }
    }

    package Subsystem_0666 {
        part def Sensor_0666 :> Common::Component {
            attribute :>> mass = 0.21 [kg];
            attribute :>> cost = 36.0;
            attribute range : Real = 116.0;
            port data : Common::DataPort;
        }
        part def Controller_0666 :> Common::Component {
            attribute :>> mass = 1.10 [kg];
            attribute :>> cost = 266.0;
            port supply : Common::PowerPort;
            part sensors : Sensor_0666[2];
            action smooth : Common::Process;
            action forward : Common::Process;
            succession first smooth then forward;
            exhibit state lifecycle : Common::Lifecycle;
        }
        requirement controllerMass_0666 : Common::MassLimit {
            subject component : Controller_0666;
            attribute :>> limit = 2.0 [kg];
        }
    }

    package Subsystem_0667 {
        part def Sensor_0667 :> Common::Component {
            attribute :>> mass = 0.22 [kg];
            attribute :>> cost = 37.0;
            attribute range : Real = 117.0;
            port data : Common::DataPort;
        }
        part def Controller_0667 :> Common::Component {
            attribute :>> mass = 1.20 [kg];
            attribute :>> cost = 267.0;
            port supply : Common::PowerPort;
            part sensors : Sensor_0667[2];
            action smooth : Common::Process;
            action forward : Common::Process;
            succession first smooth then forward;
            exhibit state lifecycle : Common::Lifecycle;
        }
        requirement controllerMass_0667 : Common::MassLimit {
            subject component : Controller_0667;
            attribute :>> limit = 2.0 [kg];
        }
    }

    package Subsystem_0668 {
        part def Sensor_0668 :> Common::Component {
            attribute :>> mass = 0.23 [kg];
            attribute :>> cost = 38.0;
            attribute range : Real = 118.0;
            port data : Common::DataPort;
        }
        part def Controller_0668 :> Common::Component {
            attribute :>> mass = 1.30 [kg];
            attribute :>> cost = 268.0;
            port supply : Common::PowerPort;
            part sensors : Sensor_0668[2];
            action smooth : Common::Process;
            action forward : Common::Process;
            succession first smooth then forward;
            exhibit state lifecycle : Common::Lifecycle;
        }
        requirement controllerMass_0668 : Common::MassLimit {
            subject component : Controller_0668;
            attribute :>> limit = 2.0 [kg];
        }
    }

    package Subsystem_0669 {
        part def Sensor_0669 :> Common::Component {
            attribute :>> mass = 0.24 [kg];
            attribute :>> cost = 39.0;
            attribute range : Real = 119.0;
            port data : Common::DataPort;
        }
        part def Controller_0669 :> Common::Component {
            attribute :>> mass = 1.40 [kg];
            attribute :>> cost = 269.0;
            port supply : Common::PowerPort;
            part sensors : Sensor_0669[2];
            action smooth : Common::Process;
            action forward : Common::Process;
            succession first smooth then forward;
            exhibit state lifecycle : Common::Lifecycle;
        }
        requirement controllerMass_0669 : Common::MassLimit {
            subject component : Controller_0669;
            attribute :>> limit = 2.0 [kg];
        }
    }

    package Subsystem_0670 {
        part def Sensor_0670 :> Common::Component {
            attribute :>> mass = 0.20 [kg];
            attribute :>> cost = 40.0;
            attribute range : Real = 120.0;
            port data : Common::DataPort;
        }
        part def Controller_0670 :> Common::Component {
            attribute :>> mass = 1.50 [kg];
            attribute :>> cost = 270.0;
            port supply : Common::PowerPort;
            part sensors : Sensor_0670[2];
            action smooth : Common::Process;
            action forward : Common::Process;
            succession first smooth then forward;
            exhibit state lifecycle : Common::Lifecycle;
        }
        requirement controllerMass_0670 : Common::MassLimit {
            subject component : Controller_0670;
            attribute :>> limit = 2.0 [kg];
        }
    }

    package Subsystem_0671 {
        part def Sensor_0671 :> Common::Component {
            attribute :>> mass = 0.21 [kg];
            attribute :>> cost = 41.0;
            attribute range : Real = 121.0;
            port data : Common::DataPort;
        }
        part def Controller_0671 :> Common::Component {
            attribute :>> mass = 1.60 [kg];
            attribute :>> cost = 271.0;
            port supply : Common::PowerPort;
            part sensors : Sensor_0671[2];
            action smooth : Common::Process;
            action forward : Common::Process;
            succession first smooth then forward;
            exhibit state lifecycle : Common::Lifecycle;
        }
        requirement controllerMass_0671 : Common::MassLimit {
            subject component : Controller_0671;
            attribute :>> limit = 2.0 [kg];
        }
    }

    package Subsystem_0672 {
        part def Sensor_0672 :> Common::Component {
            attribute :>> mass = 0.22 [kg];
            attribute :>> cost = 42.0;
            attribute range : Real = 122.0;
            port data : Common::DataPort;
        }
        part def Controller_0672 :> Common::Component {
            attribute :>> mass = 1.00 [kg];
            attribute :>> cost = 272.0;
            port supply : Common::PowerPort;
            part sensors : Sensor_0672[2];
            action smooth : Common::Process;
            action forward : Common::Process;
            succession first smooth then forward;
            exhibit state lifecycle : Common::Lifecycle;
        }
        requirement controllerMass_0672 : Common::MassLimit {
            subject component : Controller_0672;
            attribute :>> limit = 2.0 [kg];
        }
    }

    package Subsystem_0673 {
        part def Sensor_0673 :> Common::Component {
            attribute :>> mass = 0.23 [kg];
            attribute :>> cost = 43.0;
            attribute range : Real = 123.0;
            port data : Common::DataPort;
        }
        part def Controller_0673 :> Common::Component {
            attribute :>> mass = 1.10 [kg];
            attribute :>> cost = 273.0;
            port supply : Common::PowerPort;
            part sensors : Sensor_0673[2];
            action smooth : Common::Process;
            action forward : Common::Process;
            succession first smooth then forward;
            exhibit state lifecycle : Common::Lifecycle;
        }
        requirement controllerMass_0673 : Common::MassLimit {
            subject component : Controller_0673;
            attribute :>> limit = 2.0 [kg];
        }
    }

    package Subsystem_0674 {
        part def Sensor_0674 :> Common::Component {
            attribute :>> mass = 0.24 [kg];
            attribute :>> cost = 44.0;
            attribute range : Real = 124.0;
            port data : Common::DataPort;
        }
        part def Controller_0674 :> Common::Component {
            attribute :>> mass = 1.20 [kg];
            attribute :>> cost = 274.0;
            port supply : Common::PowerPort;
            part sensors : Sensor_0674[2];
            action smooth : Common::Process;
            action forward : Common::Process;
            succession first smooth then forward;
            exhibit state lifecycle : Common::Lifecycle;
        }
        requirement controllerMass_0674 : Common::MassLimit {
            subject component : Controller_0674;
            attribute :>> limit = 2.0 [kg];
        }
    }

    package Subsystem_0675 {
        part def Sensor_0675 :> Common::Component {
            attribute :>> mass = 0.20 [kg];
            attribute :>> cost = 45.0;
            attribute range : Real = 125.0;
            port data : Common::DataPort;
        }
        part def Controller_0675 :> Common::Component {
            attribute :>> mass = 1.30 [kg];
            attribute :>> cost = 275.0;
            port supply : Common::PowerPort;
            part sensors : Sensor_0675[2];
            action smooth : Common::Process;
            action forward : Common::Process;
            succession first smooth then forward;
            exhibit state lifecycle : Common::Lifecycle;
        }
        requirement controllerMass_0675 : Common::MassLimit {
            subject component : Controller_0675;
            attribute :>> limit = 2.0 [kg];
        }
    }

    package Subsystem_0676 {
        part def Sensor_0676 :> Common::Component {
            attribute :>> mass = 0.21 [kg];
            attribute :>> cost = 46.0;
            attribute range : Real = 126.0;
            port data : Common::DataPort;
        }
        part def Controller_0676 :> Common::Component {
            attribute :>> mass = 1.40 [kg];
            attribute :>> cost = 276.0;
            port supply : Common::PowerPort;
            part sensors : Sensor_0676[2];
            action smooth : Common::Process;
            action forward : Common::Process;
            succession first smooth then forward;
            exhibit state lifecycle : Common::Lifecycle;
        }
        requirement controllerMass_0676 : Common::MassLimit {
            subject component : Controller_0676;
            attribute :>> limit = 2.0 [kg];
        }
    }

    package Subsystem_0677 {
        part def Sensor_0677 :> Common::Component {
            attribute :>> mass = 0.22 [kg];
            attribute :>> cost = 47.0;
            attribute range : Real = 127.0;
            port data : Common::DataPort;
        }
        part def Controller_0677 :> Common::Component {
            attribute :>> mass = 1.50 [kg];
            attribute :>> cost = 277.0;
            port supply : Common::PowerPort;
            part sensors : Sensor_0677[2];
            action smooth : Common::Process;
            action forward : Common::Process;
            succession first smooth then forward;
            exhibit state lifecycle : Common::Lifecycle;
        }
        requirement controllerMass_0677 : Common::MassLimit {
            subject component : Controller_0677;
            attribute :>> limit = 2.0 [kg];
        }
    }

    package Subsystem_0678 {
        part def Sensor_0678 :> Common::Component {
            attribute :>> mass = 0.23 [kg];
            attribute :>> cost = 48.0;
            attribute range : Real = 128.0;
            port data : Common::DataPort;
        }
        part def Controller_0678 :> Common::Component {
            attribute :>> mass = 1.60 [kg];
            attribute :>> cost = 278.0;
            port supply : Common::PowerPort;
            part sensors : Sensor_0678[2];
            action smooth : Common::Process;
            action forward : Common::Process;
            succession first smooth then forward;
            exhibit state lifecycle : Common::Lifecycle;
        }
        requirement controllerMass_0678 : Common::MassLimit {
            subject component : Controller_0678;
            attribute :>> limit = 2.0 [kg];
        }
    }

    package Subsystem_0679 {
        part def Sensor_0679 :> Common::Component {
            attribute :>> mass = 0.24 [kg];
            attribute :>> cost = 49.0;
            attribute range : Real = 129.0;
            port data : Common::DataPort;
        }
        part def Controller_0679 :> Common::Component {
            attribute :>> mass = 1.00 [kg];
            attribute :>> cost = 279.0;
            port supply : Common::PowerPort;
            part sensors : Sensor_0679[2];
            action smooth : Common::Process;
            action forward : Common::Process;
            succession first smooth then forward;
            exhibit state lifecycle : Common::Lifecycle;
        }
        requirement controllerMass_0679 : Common::MassLimit {
            subject component : Controller_0679;
            attribute :>> limit = 2.0 [kg];
        }
    }

    package Subsystem_0680 {
        part def Sensor_0680 :> Common::Component {
            attribute :>> mass = 0.20 [kg];
            attribute :>> cost = 30.0;
            attribute range : Real = 130.0;
            port data : Common::DataPort;
        }
        part def Controller_0680 :> Common::Component {
            attribute :>> mass = 1.10 [kg];
            attribute :>> cost = 280.0;
            port supply : Common::PowerPort;
            part sensors : Sensor_0680[2];
            action smooth : Common::Process;
            action forward : Common::Process;
            succession first smooth then forward;
            exhibit state lifecycle : Common::Lifecycle;
        }
        requirement controllerMass_0680 : Common::MassLimit {
            subject component : Controller_0680;
            attribute :>> limit = 2.0 [kg];
        }
    }

    package Subsystem_0681 {
        part def Sensor_0681 :> Common::Component {
            attribute :>> mass = 0.21 [kg];
            attribute :>> cost = 31.0;
            attribute range : Real = 131.0;
            port data : Common::DataPort;
        }
        part def Controller_0681 :> Common::Component {
            attribute :>> mass = 1.20 [kg];
            attribute :>> cost = 281.0;
            port supply : Common::PowerPort;
            part sensors : Sensor_0681[2];
            action smooth : Common::Process;
            action forward : Common::Process;
            succession first smooth then forward;
            exhibit state lifecycle : Common::Lifecycle;
        }
        requirement controllerMass_0681 : Common::MassLimit {
            subject component : Controller_0681;
            attribute :>> limit = 2.0 [kg];
        }
    }

    package Subsystem_0682 {
        part def Sensor_0682 :> Common::Component {
            attribute :>> mass = 0.22 [kg];
            attribute :>> cost = 32.0;
            attribute range : Real = 132.0;
            port data : Common::DataPort;
        }
        part def Controller_0682 :> Common::Component {
            attribute :>> mass = 1.30 [kg];
            attribute :>> cost = 282.0;
            port supply : Common::PowerPort;
            part sensors : Sensor_0682[2];
            action smooth : Common::Process;
            action forward : Common::Process;
            succession first smooth then forward;
            exhibit state lifecycle : Common::Lifecycle;
        }
        requirement controllerMass_0682 : Common::MassLimit {
            subject component : Controller_0682;
            attribute :>> limit = 2.0 [kg];
        }
    }

    package Subsystem_0683 {
        part def Sensor_0683 :> Common::Component {
            attribute :>> mass = 0.23 [kg];
            attribute :>> cost = 33.0;
            attribute range : Real = 133.0;
            port data : Common::DataPort;
        }
        part def Controller_0683 :> Common::Component {
            attribute :>> mass = 1.40 [kg];
            attribute :>> cost = 283.0;
            port supply : Common::PowerPort;
            part sensors : Sensor_0683[2];
            action smooth : Common::Process;
            action forward : Common::Process;
            succession first smooth then forward;
            exhibit state lifecycle : Common::Lifecycle;
        }
        requirement controllerMass_0683 : Common::MassLimit {
            subject component : Controller_0683;
            attribute :>> limit = 2.0 [kg];
        }
    }

    package Subsystem_0684 {
        part def Sensor_0684 :> Common::Component {
            attribute :>> mass = 0.24 [kg];
            attribute :>> cost = 34.0;
            attribute range : Real = 134.0;
            port data : Common::DataPort;
        }
        part def Controller_0684 :> Common::Component {
            attribute :>> mass = 1.50 [kg];
            attribute :>> cost = 284.0;
            port supply : Common::PowerPort;
            part sensors : Sensor_0684[2];
            action smooth : Common::Process;
            action forward : Common::Process;
            succession first smooth then forward;
            exhibit state lifecycle : Common::Lifecycle;
        }
        requirement controllerMass_0684 : Common::MassLimit {
            subject component : Controller_0684;
            attribute :>> limit = 2.0 [kg];
        }
    }

    package Subsystem_0685 {
        part def Sensor_0685 :> Common::Component {
            attribute :>> mass = 0.20 [kg];
            attribute :>> cost = 35.0;
            attribute range : Real = 135.0;
            port data : Common::DataPort;
        }
        part def Controller_0685 :> Common::Component {
            attribute :>> mass = 1.60 [kg];
            attribute :>> cost = 285.0;
            port supply : Common::PowerPort;
            part sensors : Sensor_0685[2];
            action smooth : Common::Process;
            action forward : Common::Process;
            succession first smooth then forward;
            exhibit state lifecycle : Common::Lifecycle;
        }
        requirement controllerMass_0685 : Common::MassLimit {
            subject component : Controller_0685;
            attribute :>> limit = 2.0 [kg];
        }
    }

    package Subsystem_0686 {
        part def Sensor_0686 :> Common::Component {
            attribute :>> mass = 0.21 [kg];
            attribute :>> cost = 36.0;
            attribute range : Real = 136.0;
            port data : Common::DataPort;
        }
        part def Controller_0686 :> Common::Component {
            attribute :>> mass = 1.00 [kg];
            attribute :>> cost = 286.0;
            port supply : Common::PowerPort;
            part sensors : Sensor_0686[2];
            action smooth : Common::Process;
            action forward : Common::Process;
            succession first smooth then forward;
            exhibit state lifecycle : Common::Lifecycle;
        }
        requirement controllerMass_0686 : Common::MassLimit {
            subject component : Controller_0686;
            attribute :>> limit = 2.0 [kg];
        }
    }

    package Subsystem_0687 {
        part def Sensor_0687 :> Common::Component {
            attribute :>> mass = 0.22 [kg];
            attribute :>> cost = 37.0;
            attribute range : Real = 137.0;
            port data : Common::DataPort;
        }
        part def Controller_0687 :> Common::Component {
            attribute :>> mass = 1.10 [kg];
            attribute :>> cost = 287.0;
            port supply : Common::PowerPort;
            part sensors : Sensor_0687[2];
            action smooth : Common::Process;
            action forward : Common::Process;
            succession first smooth then forward;
            exhibit state lifecycle : Common::Lifecycle;
        }
        requirement controllerMass_0687 : Common::MassLimit {
            subject component : Controller_0687;
            attribute :>> limit = 2.0 [kg];
        }
    }

    package Subsystem_0688 {
        part def Sensor_0688 :> Common::Component {
            attribute :>> mass = 0.23 [kg];
            attribute :>> cost = 38.0;
            attribute range : Real = 138.0;
            port data : Common::DataPort;
        }
        part def Controller_0688 :> Common::Component {
            attribute :>> mass = 1.20 [kg];
            attribute :>> cost = 288.0;
            port supply : Common::PowerPort;
            part sensors : Sensor_0688[2];
            action smooth : Common::Process;
            action forward : Common::Process;
            succession first smooth then forward;
            exhibit state lifecycle : Common::Lifecycle;
        }
        requirement controllerMass_0688 : Common::MassLimit {
            subject component : Controller_0688;
            attribute :>> limit = 2.0 [kg];
        }
    }

    package Subsystem_0689 {
        part def Sensor_0689 :> Common::Component {
            attribute :>> mass = 0.24 [kg];
            attribute :>> cost = 39.0;
            attribute range : Real = 139.0;
            port data : Common::DataPort;
        }
        part def Controller_0689 :> Common::Component {
            attribute :>> mass = 1.30 [kg];
            attribute :>> cost = 289.0;
            port supply : Common::PowerPort;
            part sensors : Sensor_0689[2];
            action smooth : Common::Process;
            action forward : Common::Process;
            succession first smooth then forward;
            exhibit state lifecycle : Common::Lifecycle;
        }
        requirement controllerMass_0689 : Common::MassLimit {
            subject component : Controller_0689;
            attribute :>> limit = 2.0 [kg];
        }
    }

    package Subsystem_0690 {
        part def Sensor_0690 :> Common::Component {
            attribute :>> mass = 0.20 [kg];
            attribute :>> cost = 40.0;
            attribute range : Real = 140.0;
            port data : Common::DataPort;
        }
        part def Controller_0690 :> Common::Component {
            attribute :>> mass = 1.40 [kg];
            attribute :>> cost = 290.0;
            port supply : Common::PowerPort;
            part sensors : Sensor_0690[2];
            action smooth : Common::Process;
            action forward : Common::Process;
            succession first smooth then forward;
            exhibit state lifecycle : Common::Lifecycle;
        }
        requirement controllerMass_0690 : Common::MassLimit {
            subject component : Controller_0690;
            attribute :>> limit = 2.0 [kg];
        }
    }

    package Subsystem_0691 {
        part def Sensor_0691 :> Common::Component {
            attribute :>> mass = 0.21 [kg];
            attribute :>> cost = 41.0;
            attribute range : Real = 141.0;
            port data : Common::DataPort;
        }
        part def Controller_0691 :> Common::Component {
            attribute :>> mass = 1.50 [kg];
            attribute :>> cost = 291.0;
            port supply : Common::PowerPort;
            part sensors : Sensor_0691[2];
            action smooth : Common::Process;
            action forward : Common::Process;
            succession first smooth then forward;
            exhibit state lifecycle : Common::Lifecycle;
        }
        requirement controllerMass_0691 : Common::MassLimit {
            subject component : Controller_0691;
            attribute :>> limit = 2.0 [kg];
        }
    }

    package Subsystem_0692 {
        part def Sensor_0692 :> Common::Component {
            attribute :>> mass = 0.22 [kg];
            attribute :>> cost = 42.0;
            attribute range : Real = 142.0;
            port data : Common::DataPort;
        }
        part def Controller_0692 :> Common::Component {
            attribute :>> mass = 1.60 [kg];
            attribute :>> cost = 292.0;
            port supply : Common::PowerPort;
            part sensors : Sensor_0692[2];
            action smooth : Common::Process;
            action forward : Common::Process;
            succession first smooth then forward;
            exhibit state lifecycle : Common::Lifecycle;
        }
        requirement controllerMass_0692 : Common::MassLimit {
            subject component : Controller_0692;
            attribute :>> limit = 2.0 [kg];
        }
    }

    package Subsystem_0693 {
        part def Sensor_0693 :> Common::Component {
            attribute :>> mass = 0.23 [kg];
            attribute :>> cost = 43.0;
            attribute range : Real = 143.0;
            port data : Common::DataPort;
        }
        part def Controller_0693 :> Common::Component {
            attribute :>> mass = 1.00 [kg];
            attribute :>> cost = 293.0;
            port supply : Common::PowerPort;
            part sensors : Sensor_0693[2];
            action smooth : Common::Process;
            action forward : Common::Process;
            succession first smooth then forward;
            exhibit state lifecycle : Common::Lifecycle;
        }
        requirement controllerMass_0693 : Common::MassLimit {
            subject component : Controller_0693;
            attribute :>> limit = 2.0 [kg];
        }
    }

    package Subsystem_0694 {
        part def Sensor_0694 :> Common::Component {
            attribute :>> mass = 0.24 [kg];
            attribute :>> cost = 44.0;
            attribute range : Real = 144.0;
            port data : Common::DataPort;
        }
        part def Controller_0694 :> Common::Component {
            attribute :>> mass = 1.10 [kg];
            attribute :>> cost = 294.0;
            port supply : Common::PowerPort;
            part sensors : Sensor_0694[2];
            action smooth : Common::Process;
            action forward : Common::Process;
            succession first smooth then forward;
            exhibit state lifecycle : Common::Lifecycle;
        }
        requirement controllerMass_0694 : Common::MassLimit {
            subject component : Controller_0694;
            attribute :>> limit = 2.0 [kg];
        }
    }

    package Subsystem_0695 {
        part def Sensor_0695 :> Common::Component {
            attribute :>> mass = 0.20 [kg];
            attribute :>> cost = 45.0;
            attribute range : Real = 145.0;
            port data : Common::DataPort;
        }
        part def Controller_0695 :> Common::Component {
            attribute :>> mass = 1.20 [kg];
            attribute :>> cost = 295.0;
            port supply : Common::PowerPort;
            part sensors : Sensor_0695[2];
            action smooth : Common::Process;
            action forward : Common::Process;
            succession first smooth then forward;
            exhibit state lifecycle : Common::Lifecycle;
        }
        requirement controllerMass_0695 : Common::MassLimit {
            subject component : Controller_0695;
            attribute :>> limit = 2.0 [kg];
        }
    }

    package Subsystem_0696 {
        part def Sensor_0696 :> Common::Component {
            attribute :>> mass = 0.21 [kg];
            attribute :>> cost = 46.0;
            attribute range : Real = 146.0;
            port data : Common::DataPort;
        }
        part def Controller_0696 :> Common::Component {
            attribute :>> mass = 1.30 [kg];
            attribute :>> cost = 296.0;
            port supply : Common::PowerPort;
            part sensors : Sensor_0696[2];
            action smooth : Common::Process;
            action forward : Common::Process;
            succession first smooth then forward;
            exhibit state lifecycle : Common::Lifecycle;
        }
        requirement controllerMass_0696 : Common::MassLimit {
            subject component : Controller_0696;
            attribute :>> limit = 2.0 [kg];
        }
    }

    package Subsystem_0697 {
        part def Sensor_0697 :> Common::Component {
            attribute :>> mass = 0.22 [kg];
            attribute :>> cost = 47.0;
            attribute range : Real = 147.0;
            port data : Common::DataPort;
        }
        part def Controller_0697 :> Common::Component {
            attribute :>> mass = 1.40 [kg];
            attribute :>> cost = 297.0;
            port supply : Common::PowerPort;
            part sensors : Sensor_0697[2];
            action smooth : Common::Process;
            action forward : Common::Process;
            succession first smooth then forward;
            exhibit state lifecycle : Common::Lifecycle;
        }
        requirement controllerMass_0697 : Common::MassLimit {
            subject component : Controller_0697;
            attribute :>> limit = 2.0 [kg];
        }
    }

    package Subsystem_0698 {
        part def Sensor_0698 :> Common::Component {
            attribute :>> mass = 0.23 [kg];
            attribute :>> cost = 48.0;
            attribute range : Real = 148.0;
            port data : Common::DataPort;
        }
        part def Controller_0698 :> Common::Component {
            attribute :>> mass = 1.50 [kg];
            attribute :>> cost = 298.0;
            port supply : Common::PowerPort;
            part sensors : Sensor_0698[2];
            action smooth : Common::Process;
            action forward : Common::Process;
            succession first smooth then forward;
            exhibit state lifecycle : Common::Lifecycle;
        }
        requirement controllerMass_0698 : Common::MassLimit {
            subject component : Controller_0698;
            attribute :>> limit = 2.0 [kg];
        }
    }

    package Subsystem_0699 {
        part def Sensor_0699 :> Common::Component {
            attribute :>> mass = 0.24 [kg];
            attribute :>> cost = 49.0;
            attribute range : Real = 149.0;
            port data : Common::DataPort;
        }
        part def Controller_0699 :> Common::Component {
            attribute :>> mass = 1.60 [kg];
            attribute :>> cost = 299.0;
            port supply : Common::PowerPort;
            part sensors : Sensor_0699[2];
            action smooth : Common::Process;
            action forward : Common::Process;
            succession first smooth then forward;
            exhibit state lifecycle : Common::Lifecycle;
        }
        requirement controllerMass_0699 : Common::MassLimit {
            subject component : Controller_0699;
            attribute :>> limit = 2.0 [kg];
        }
    }

    package Subsystem_0700 {
        part def Sensor_0700 :> Common::Component {
            attribute :>> mass = 0.20 [kg];
            attribute :>> cost = 30.0;
            attribute range : Real = 100.0;
            port data : Common::DataPort;
        }
        part def Controller_0700 :> Common::Component {
            attribute :>> mass = 1.00 [kg];
            attribute :>> cost = 200.0;
            port supply : Common::PowerPort;
            part sensors : Sensor_0700[2];
            action smooth : Common::Process;
            action forward : Common::Process;
            succession first smooth then forward;
            exhibit state lifecycle : Common::Lifecycle;
        }
        requirement controllerMass_0700 : Common::MassLimit {
            subject component : Controller_0700;
            attribute :>> limit = 2.0 [kg];
        }
    }

    package Subsystem_0701 {
        part def Sensor_0701 :> Common::Component {
            attribute :>> mass = 0.21 [kg];
            attribute :>> cost = 31.0;
            attribute range : Real = 101.0;
            port data : Common::DataPort;
        }
        part def Controller_0701 :> Common::Component {
            attribute :>> mass = 1.10 [kg];
            attribute :>> cost = 201.0;
            port supply : Common::PowerPort;
            part sensors : Sensor_0701[2];
            action smooth : Common::Process;
            action forward : Common::Process;
            succession first smooth then forward;
            exhibit state lifecycle : Common::Lifecycle;
        }
        requirement controllerMass_0701 : Common::MassLimit {
            subject component : Controller_0701;
            attribute :>> limit = 2.0 [kg];
        }
    }

    package Subsystem_0702 {
        part def Sensor_0702 :> Common::Component {
            attribute :>> mass = 0.22 [kg];
            attribute :>> cost = 32.0;
            attribute range : Real = 102.0;
            port data : Common::DataPort;
        }
        part def Controller_0702 :> Common::Component {
            attribute :>> mass = 1.20 [kg];
            attribute :>> cost = 202.0;
            port supply : Common::PowerPort;
            part sensors : Sensor_0702[2];
            action smooth : Common::Process;
            action forward : Common::Process;
            succession first smooth then forward;
            exhibit state lifecycle : Common::Lifecycle;
        }
        requirement controllerMass_0702 : Common::MassLimit {
            subject component : Controller_0702;
            attribute :>> limit = 2.0 [kg];
        }
    }

    package Subsystem_0703 {
        part def Sensor_0703 :> Common::Component {
            attribute :>> mass = 0.23 [kg];
            attribute :>> cost = 33.0;
            attribute range : Real = 103.0;
            port data : Common::DataPort;
        }
        part def Controller_0703 :> Common::Component {
            attribute :>> mass = 1.30 [kg];
            attribute :>> cost = 203.0;
            port supply : Common::PowerPort;
            part sensors : Sensor_0703[2];
            action smooth : Common::Process;
            action forward : Common::Process;
            succession first smooth then forward;
            exhibit state lifecycle : Common::Lifecycle;
        }
        requirement controllerMass_0703 : Common::MassLimit {
            subject component : Controller_0703;
            attribute :>> limit = 2.0 [kg];
        }
    }

    package Subsystem_0704 {
        part def Sensor_0704 :> Common::Component {
            attribute :>> mass = 0.24 [kg];
            attribute :>> cost = 34.0;
            attribute range : Real = 104.0;
            port data : Common::DataPort;
        }
        part def Controller_0704 :> Common::Component {
            attribute :>> mass = 1.40 [kg];
            attribute :>> cost = 204.0;
            port supply : Common::PowerPort;
            part sensors : Sensor_0704[2];
            action smooth : Common::Process;
            action forward : Common::Process;
            succession first smooth then forward;
            exhibit state lifecycle : Common::Lifecycle;
        }
        requirement controllerMass_0704 : Common::MassLimit {
            subject component : Controller_0704;
            attribute :>> limit = 2.0 [kg];
        }
    }

    package Subsystem_0705 {
        part def Sensor_0705 :> Common::Component {
            attribute :>> mass = 0.20 [kg];
            attribute :>> cost = 35.0;
            attribute range : Real = 105.0;
            port data : Common::DataPort;
        }
        part def Controller_0705 :> Common::Component {
            attribute :>> mass = 1.50 [kg];
            attribute :>> cost = 205.0;
            port supply : Common::PowerPort;
            part sensors : Sensor_0705[2];
            action smooth : Common::Process;
            action forward : Common::Process;
            succession first smooth then forward;
            exhibit state lifecycle : Common::Lifecycle;
        }
        requirement controllerMass_0705 : Common::MassLimit {
            subject component : Controller_0705;
            attribute :>> limit = 2.0 [kg];
        }
    }

    package Subsystem_0706 {
        part def Sensor_0706 :> Common::Component {
            attribute :>> mass = 0.21 [kg];
            attribute :>> cost = 36.0;
            attribute range : Real = 106.0;
            port data : Common::DataPort;
        }
        part def Controller_0706 :> Common::Component {
            attribute :>> mass = 1.60 [kg];
            attribute :>> cost = 206.0;
            port supply : Common::PowerPort;
            part sensors : Sensor_0706[2];
            action smooth : Common::Process;
            action forward : Common::Process;
            succession first smooth then forward;
            exhibit state lifecycle : Common::Lifecycle;
        }
        requirement controllerMass_0706 : Common::MassLimit {
            subject component : Controller_0706;
            attribute :>> limit = 2.0 [kg];
        }
    }

    package Subsystem_0707 {
        part def Sensor_0707 :> Common::Component {
            attribute :>> mass = 0.22 [kg];
            attribute :>> cost = 37.0;
            attribute range : Real = 107.0;
            port data : Common::DataPort;
        }
        part def Controller_0707 :> Common::Component {
            attribute :>> mass = 1.00 [kg];
            attribute :>> cost = 207.0;
            port supply : Common::PowerPort;
            part sensors : Sensor_0707[2];
            action smooth : Common::Process;
            action forward : Common::Process;
            succession first smooth then forward;
            exhibit state lifecycle : Common::Lifecycle;
        }
        requirement controllerMass_0707 : Common::MassLimit {
            subject component : Controller_0707;
            attribute :>> limit = 2.0 [kg];
        }
    }

    package Subsystem_0708 {
        part def Sensor_0708 :> Common::Component {
            attribute :>> mass = 0.23 [kg];
            attribute :>> cost = 38.0;
            attribute range : Real = 108.0;
            port data : Common::DataPort;
        }
        part def Controller_0708 :> Common::Component {
            attribute :>> mass = 1.10 [kg];
            attribute :>> cost = 208.0;
            port supply : Common::PowerPort;
            part sensors : Sensor_0708[2];
            action smooth : Common::Process;
            action forward : Common::Process;
            succession first smooth then forward;
            exhibit state lifecycle : Common::Lifecycle;
        }
        requirement controllerMass_0708 : Common::MassLimit {
            subject component : Controller_0708;
            attribute :>> limit = 2.0 [kg];
        }
    }

    package Subsystem_0709 {
        part def Sensor_0709 :> Common::Component {
            attribute :>> mass = 0.24 [kg];
            attribute :>> cost = 39.0;
            attribute range : Real = 109.0;
            port data : Common::DataPort;
        }
        part def Controller_0709 :> Common::Component {
            attribute :>> mass = 1.20 [kg];
            attribute :>> cost = 209.0;
            port supply : Common::PowerPort;
            part sensors : Sensor_0709[2];
            action smooth : Common::Process;
            action forward : Common::Process;
            succession first smooth then forward;
            exhibit state lifecycle : Common::Lifecycle;
        }
        requirement controllerMass_0709 : Common::MassLimit {
            subject component : Controller_0709;
            attribute :>> limit = 2.0 [kg];
        }
    }

    package Subsystem_0710 {
        part def Sensor_0710 :> Common::Component {
            attribute :>> mass = 0.20 [kg];
            attribute :>> cost = 40.0;
            attribute range : Real = 110.0;
            port data : Common::DataPort;
        }
        part def Controller_0710 :> Common::Component {
            attribute :>> mass = 1.30 [kg];
            attribute :>> cost = 210.0;
            port supply : Common::PowerPort;
            part sensors : Sensor_0710[2];
            action smooth : Common::Process;
            action forward : Common::Process;
            succession first smooth then forward;
            exhibit state lifecycle : Common::Lifecycle;
        }
        requirement controllerMass_0710 : Common::MassLimit {
            subject component : Controller_0710;
            attribute :>> limit = 2.0 [kg];
        }
    }

    package Subsystem_0711 {
        part def Sensor_0711 :> Common::Component {
            attribute :>> mass = 0.21 [kg];
            attribute :>> cost = 41.0;
            attribute range : Real = 111.0;
            port data : Common::DataPort;
        }
        part def Controller_0711 :> Common::Component {
            attribute :>> mass = 1.40 [kg];
            attribute :>> cost = 211.0;
            port supply : Common::PowerPort;
            part sensors : Sensor_0711[2];
            action smooth : Common::Process;
            action forward : Common::Process;
            succession first smooth then forward;
            exhibit state lifecycle : Common::Lifecycle;
        }
        requirement controllerMass_0711 : Common::MassLimit {
            subject component : Controller_0711;
            attribute :>> limit = 2.0 [kg];
        }
    }

    package Subsystem_0712 {
        part def Sensor_0712 :> Common::Component {
            attribute :>> mass = 0.22 [kg];
            attribute :>> cost = 42.0;
            attribute range : Real = 112.0;
            port data : Common::DataPort;
        }
        part def Controller_0712 :> Common::Component {
            attribute :>> mass = 1.50 [kg];
            attribute :>> cost = 212.0;
            port supply : Common::PowerPort;
            part sensors : Sensor_0712[2];
            action smooth : Common::Process;
            action forward : Common::Process;
            succession first smooth then forward;
            exhibit state lifecycle : Common::Lifecycle;
        }
        requirement controllerMass_0712 : Common::MassLimit {
            subject component : Controller_0712;
            attribute :>> limit = 2.0 [kg];
        }
    }

    package Subsystem_0713 {
        part def Sensor_0713 :> Common::Component {
            attribute :>> mass = 0.23 [kg];
            attribute :>> cost = 43.0;
            attribute range : Real = 113.0;
            port data : Common::DataPort;
        }
        part def Controller_0713 :> Common::Component {
            attribute :>> mass = 1.60 [kg];
            attribute :>> cost = 213.0;
            port supply : Common::PowerPort;
            part sensors : Sensor_0713[2];
            action smooth : Common::Process;
            action forward : Common::Process;
            succession first smooth then forward;
            exhibit state lifecycle : Common::Lifecycle;
        }
        requirement controllerMass_0713 : Common::MassLimit {
            subject component : Controller_0713;
            attribute :>> limit = 2.0 [kg];
        }
    }

    package Subsystem_0714 {
        part def Sensor_0714 :> Common::Component {
            attribute :>> mass = 0.24 [kg];
            attribute :>> cost = 44.0;
            attribute range : Real = 114.0;
            port data : Common::DataPort;
        }
        part def Controller_0714 :> Common::Component {
            attribute :>> mass = 1.00 [kg];
            attribute :>> cost = 214.0;
            port supply : Common::PowerPort;
            part sensors : Sensor_0714[2];
            action smooth : Common::Process;
            action forward : Common::Process;
            succession first smooth then forward;
            exhibit state lifecycle : Common::Lifecycle;
        }
        requirement controllerMass_0714 : Common::MassLimit {
            subject component : Controller_0714;
            attribute :>> limit = 2.0 [kg];
        }
    }

    package Subsystem_0715 {
        part def Sensor_0715 :> Common::Component {
            attribute :>> mass = 0.20 [kg];
            attribute :>> cost = 45.0;
            attribute range : Real = 115.0;
            port data : Common::DataPort;
        }
        part def Controller_0715 :> Common::Component {
            attribute :>> mass = 1.10 [kg];
            attribute :>> cost = 215.0;
            port supply : Common::PowerPort;
            part sensors : Sensor_0715[2];
            action smooth : Common::Process;
            action forward : Common::Process;
            succession first smooth then forward;
            exhibit state lifecycle : Common::Lifecycle;
        }
        requirement controllerMass_0715 : Common::MassLimit {
            subject component : Controller_0715;
            attribute :>> limit = 2.0 [kg];
        }
    }

    package Subsystem_0716 {
        part def Sensor_0716 :> Common::Component {
            attribute :>> mass = 0.21 [kg];
            attribute :>> cost = 46.0;
            attribute range : Real = 116.0;
            port data : Common::DataPort;
        }
        part def Controller_0716 :> Common::Component {
            attribute :>> mass = 1.20 [kg];
            attribute :>> cost = 216.0;
            port supply : Common::PowerPort;
            part sensors : Sensor_0716[2];
            action smooth : Common::Process;
            action forward : Common::Process;
            succession first smooth then forward;
            exhibit state lifecycle : Common::Lifecycle;
        }
        requirement controllerMass_0716 : Common::MassLimit {
            subject component : Controller_0716;
            attribute :>> limit = 2.0 [kg];
        }
    }

    package Subsystem_0717 {
        part def Sensor_0717 :> Common::Component {
            attribute :>> mass = 0.22 [kg];
            attribute :>> cost = 47.0;
            attribute range : Real = 117.0;
            port data : Common::DataPort;
        }
        part def Controller_0717 :> Common::Component {
            attribute :>> mass = 1.30 [kg];
            attribute :>> cost = 217.0;
            port supply : Common::PowerPort;
            part sensors : Sensor_0717[2];
            action smooth : Common::Process;
            action forward : Common::Process;
            succession first smooth then forward;
            exhibit state lifecycle : Common::Lifecycle;
        }
        requirement controllerMass_0717 : Common::MassLimit {
            subject component : Controller_0717;
            attribute :>> limit = 2.0 [kg];
        }
    }

    package Subsystem_0718 {
        part def Sensor_0718 :> Common::Component {
            attribute :>> mass = 0.23 [kg];
            attribute :>> cost = 48.0;
            attribute range : Real = 118.0;
            port data : Common::DataPort;
        }
        part def Controller_0718 :> Common::Component {
            attribute :>> mass = 1.40 [kg];
            attribute :>> cost = 218.0;
            port supply : Common::PowerPort;
            part sensors : Sensor_0718[2];
            action smooth : Common::Process;
            action forward : Common::Process;
            succession first smooth then forward;
            exhibit state lifecycle : Common::Lifecycle;
        }
        requirement controllerMass_0718 : Common::MassLimit {
            subject component : Controller_0718;
            attribute :>> limit = 2.0 [kg];
        }
    }

    package Subsystem_0719 {
        part def Sensor_0719 :> Common::Component {
            attribute :>> mass = 0.24 [kg];
            attribute :>> cost = 49.0;
            attribute range : Real = 119.0;
            port data : Common::DataPort;
        }
        part def Controller_0719 :> Common::Component {
            attribute :>> mass = 1.50 [kg];
            attribute :>> cost = 219.0;
            port supply : Common::PowerPort;
            part sensors : Sensor_0719[2];
            action smooth : Common::Process;
            action forward : Common::Process;
            succession first smooth then forward;
            exhibit state lifecycle : Common::Lifecycle;
        }
        requirement controllerMass_0719 : Common::MassLimit {
            subject component : Controller_0719;
            attribute :>> limit = 2.0 [kg];
        }
    }

    package Subsystem_0720 {
        part def Sensor_0720 :> Common::Component {
            attribute :>> mass = 0.20 [kg];
            attribute :>> cost = 30.0;
            attribute range : Real = 120.0;
            port data : Common::DataPort;
        }
        part def Controller_0720 :> Common::Component {
            attribute :>> mass = 1.60 [kg];
            attribute :>> cost = 220.0;
            port supply : Common::PowerPort;
            part sensors : Sensor_0720[2];
            action smooth : Common::Process;
            action forward : Common::Process;
            succession first smooth then forward;
            exhibit state lifecycle : Common::Lifecycle;
        }
        requirement controllerMass_0720 : Common::MassLimit {
            subject component : Controller_0720;
            attribute :>> limit = 2.0 [kg];
        }
    }

    package Subsystem_0721 {
        part def Sensor_0721 :> Common::Component {
            attribute :>> mass = 0.21 [kg];
            attribute :>> cost = 31.0;
            attribute range : Real = 121.0;
            port data : Common::DataPort;
        }
        part def Controller_0721 :> Common::Component {
            attribute :>> mass = 1.00 [kg];
            attribute :>> cost = 221.0;
            port supply : Common::PowerPort;
            part sensors : Sensor_0721[2];
            action smooth : Common::Process;
            action forward : Common::Process;
            succession first smooth then forward;
            exhibit state lifecycle : Common::Lifecycle;
        }
        requirement controllerMass_0721 : Common::MassLimit {
            subject component : Controller_0721;
            attribute :>> limit = 2.0 [kg];
        }
    }

    package Subsystem_0722 {
        part def Sensor_0722 :> Common::Component {
            attribute :>> mass = 0.22 [kg];
            attribute :>> cost = 32.0;
            attribute range : Real = 122.0;
            port data : Common::DataPort;
        }
        part def Controller_0722 :> Common::Component {
            attribute :>> mass = 1.10 [kg];
            attribute :>> cost = 222.0;
            port supply : Common::PowerPort;
            part sensors : Sensor_0722[2];
            action smooth : Common::Process;
            action forward : Common::Process;
            succession first smooth then forward;
            exhibit state lifecycle : Common::Lifecycle;
        }
        requirement controllerMass_0722 : Common::MassLimit {
            subject component : Controller_0722;
            attribute :>> limit = 2.0 [kg];
        }
    }

    package Subsystem_0723 {
        part def Sensor_0723 :> Common::Component {
            attribute :>> mass = 0.23 [kg];
            attribute :>> cost = 33.0;
            attribute range : Real = 123.0;
            port data : Common::DataPort;
        }
        part def Controller_0723 :> Common::Component {
            attribute :>> mass = 1.20 [kg];
            attribute :>> cost = 223.0;
            port supply : Common::PowerPort;
            part sensors : Sensor_0723[2];
            action smooth : Common::Process;
            action forward : Common::Process;
            succession first smooth then forward;
            exhibit state lifecycle : Common::Lifecycle;
        }
        requirement controllerMass_0723 : Common::MassLimit {
            subject component : Controller_0723;
            attribute :>> limit = 2.0 [kg];
        }
    }

    package Subsystem_0724 {
        part def Sensor_0724 :> Common::Component {
            attribute :>> mass = 0.24 [kg];
            attribute :>> cost = 34.0;
            attribute range : Real = 124.0;
            port data : Common::DataPort;
        }
        part def Controller_0724 :> Common::Component {
            attribute :>> mass = 1.30 [kg];
            attribute :>> cost = 224.0;
            port supply : Common::PowerPort;
            part sensors : Sensor_0724[2];
            action smooth : Common::Process;
            action forward : Common::Process;
            succession first smooth then forward;
            exhibit state lifecycle : Common::Lifecycle;
        }
        requirement controllerMass_0724 : Common::MassLimit {
            subject component : Controller_0724;
            attribute :>> limit = 2.0 [kg];
        }
    }

    package Subsystem_0725 {
        part def Sensor_0725 :> Common::Component {
            attribute :>> mass = 0.20 [kg];
            attribute :>> cost = 35.0;
            attribute range : Real = 125.0;
            port data : Common::DataPort;
        }
        part def Controller_0725 :> Common::Component {
            attribute :>> mass = 1.40 [kg];
            attribute :>> cost = 225.0;
            port supply : Common::PowerPort;
            part sensors : Sensor_0725[2];
            action smooth : Common::Process;
            action forward : Common::Process;
            succession first smooth then forward;
            exhibit state lifecycle : Common::Lifecycle;
        }
        requirement controllerMass_0725 : Common::MassLimit {
            subject component : Controller_0725;
            attribute :>> limit = 2.0 [kg];
        }
    }

    package Subsystem_0726 {
        part def Sensor_0726 :> Common::Component {
            attribute :>> mass = 0.21 [kg];
            attribute :>> cost = 36.0;
            attribute range : Real = 126.0;
            port data : Common::DataPort;
        }
        part def Controller_0726 :> Common::Component {
            attribute :>> mass = 1.50 [kg];
            attribute :>> cost = 226.0;
            port supply : Common::PowerPort;
            part sensors : Sensor_0726[2];
            action smooth : Common::Process;
            action forward : Common::Process;
            succession first smooth then forward;
            exhibit state lifecycle : Common::Lifecycle;
        }
        requirement controllerMass_0726 : Common::MassLimit {
            subject component : Controller_0726;
            attribute :>> limit = 2.0 [kg];
        }
    }

    package Subsystem_0727 {
        part def Sensor_0727 :> Common::Component {
            attribute :>> mass = 0.22 [kg];
            attribute :>> cost = 37.0;
            attribute range : Real = 127.0;
            port data : Common::DataPort;
        }
        part def Controller_0727 :> Common::Component {
            attribute :>> mass = 1.60 [kg];
            attribute :>> cost = 227.0;
            port supply : Common::PowerPort;
            part sensors : Sensor_0727[2];
            action smooth : Common::Process;
            action forward : Common::Process;
            succession first smooth then forward;
            exhibit state lifecycle : Common::Lifecycle;
        }
        requirement controllerMass_0727 : Common::MassLimit {
            subject component : Controller_0727;
            attribute :>> limit = 2.0 [kg];
        }
    }

    package Subsystem_0728 {
        part def Sensor_0728 :> Common::Component {
            attribute :>> mass = 0.23 [kg];
            attribute :>> cost = 38.0;
            attribute range : Real = 128.0;
            port data : Common::DataPort;
        }
        part def Controller_0728 :> Common::Component {
            attribute :>> mass = 1.00 [kg];
            attribute :>> cost = 228.0;
            port supply : Common::PowerPort;
            part sensors : Sensor_0728[2];
            action smooth : Common::Process;
            action forward : Common::Process;
            succession first smooth then forward;
            exhibit state lifecycle : Common::Lifecycle;
        }
        requirement controllerMass_0728 : Common::MassLimit {
            subject component : Controller_0728;
            attribute :>> limit = 2.0 [kg];
        }
    }

    package Subsystem_0729 {
        part def Sensor_0729 :> Common::Component {
            attribute :>> mass = 0.24 [kg];
            attribute :>> cost = 39.0;
            attribute range : Real = 129.0;
            port data : Common::DataPort;
        }
        part def Controller_0729 :> Common::Component {
            attribute :>> mass = 1.10 [kg];
            attribute :>> cost = 229.0;
            port supply : Common::PowerPort;
            part sensors : Sensor_0729[2];
            action smooth : Common::Process;
            action forward : Common::Process;
            succession first smooth then forward;
            exhibit state lifecycle : Common::Lifecycle;
        }
        requirement controllerMass_0729 : Common::MassLimit {
            subject component : Controller_0729;
            attribute :>> limit = 2.0 [kg];
        }
    }

    package Subsystem_0730 {
        part def Sensor_0730 :> Common::Component {
            attribute :>> mass = 0.20 [kg];
            attribute :>> cost = 40.0;
            attribute range : Real = 130.0;
            port data : Common::DataPort;
        }
        part def Controller_0730 :> Common::Component {
            attribute :>> mass = 1.20 [kg];
            attribute :>> cost = 230.0;
            port supply : Common::PowerPort;
            part sensors : Sensor_0730[2];
            action smooth : Common::Process;
            action forward : Common::Process;
            succession first smooth then forward;
            exhibit state lifecycle : Common::Lifecycle;
        }
        requirement controllerMass_0730 : Common::MassLimit {
            subject component : Controller_0730;
            attribute :>> limit = 2.0 [kg];
        }
    }

    package Subsystem_0731 {
        part def Sensor_0731 :> Common::Component {
            attribute :>> mass = 0.21 [kg];
            attribute :>> cost = 41.0;
            attribute range : Real = 131.0;
            port data : Common::DataPort;
        }
        part def Controller_0731 :> Common::Component {
            attribute :>> mass = 1.30 [kg];
            attribute :>> cost = 231.0;
            port supply : Common::PowerPort;
            part sensors : Sensor_0731[2];
            action smooth : Common::Process;
            action forward : Common::Process;
            succession first smooth then forward;
            exhibit state lifecycle : Common::Lifecycle;
        }
        requirement controllerMass_0731 : Common::MassLimit {
            subject component : Controller_0731;
            attribute :>> limit = 2.0 [kg];
        }
    }

    package Subsystem_0732 {
        part def Sensor_0732 :> Common::Component {
            attribute :>> mass = 0.22 [kg];
            attribute :>> cost = 42.0;
            attribute range : Real = 132.0;
            port data : Common::DataPort;
        }
        part def Controller_0732 :> Common::Component {
            attribute :>> mass = 1.40 [kg];
            attribute :>> cost = 232.0;
            port supply : Common::PowerPort;
            part sensors : Sensor_0732[2];
            action smooth : Common::Process;
            action forward : Common::Process;
            succession first smooth then forward;
            exhibit state lifecycle : Common::Lifecycle;
        }
        requirement controllerMass_0732 : Common::MassLimit {
            subject component : Controller_0732;
            attribute :>> limit = 2.0 [kg];
        }
    }

    package Subsystem_0733 {
        part def Sensor_0733 :> Common::Component {
            attribute :>> mass = 0.23 [kg];
            attribute :>> cost = 43.0;
            attribute range : Real = 133.0;
            port data : Common::DataPort;
        }
        part def Controller_0733 :> Common::Component {
            attribute :>> mass = 1.50 [kg];
            attribute :>> cost = 233.0;
            port supply : Common::PowerPort;
            part sensors : Sensor_0733[2];
            action smooth : Common::Process;
            action forward : Common::Process;
            succession first smooth then forward;
            exhibit state lifecycle : Common::Lifecycle;
        }
        requirement controllerMass_0733 : Common::MassLimit {
            subject component : Controller_0733;
            attribute :>> limit = 2.0 [kg];
        }
    }

    package Subsystem_0734 {
        part def Sensor_0734 :> Common::Component {
            attribute :>> mass = 0.24 [kg];
            attribute :>> cost = 44.0;
            attribute range : Real = 134.0;
            port data : Common::DataPort;
        }
        part def Controller_0734 :> Common::Component {
            attribute :>> mass = 1.60 [kg];
            attribute :>> cost = 234.0;
            port supply : Common::PowerPort;
            part sensors : Sensor_0734[2];
            action smooth : Common::Process;
            action forward : Common::Process;
            succession first smooth then forward;
            exhibit state lifecycle : Common::Lifecycle;
        }
        requirement controllerMass_0734 : Common::MassLimit {
            subject component : Controller_0734;
            attribute :>> limit = 2.0 [kg];
        }
    }

    package Subsystem_0735 {
        part def Sensor_0735 :> Common::Component {
            attribute :>> mass = 0.20 [kg];
            attribute :>> cost = 45.0;
            attribute range : Real = 135.0;
            port data : Common::DataPort;
        }
        part def Controller_0735 :> Common::Component {
            attribute :>> mass = 1.00 [kg];
            attribute :>> cost = 235.0;
            port supply : Common::PowerPort;
            part sensors : Sensor_0735[2];
            action smooth : Common::Process;
            action forward : Common::Process;
            succession first smooth then forward;
            exhibit state lifecycle : Common::Lifecycle;
        }
        requirement controllerMass_0735 : Common::MassLimit {
            subject component : Controller_0735;
            attribute :>> limit = 2.0 [kg];
        }
    }

    package Subsystem_0736 {
        part def Sensor_0736 :> Common::Component {
            attribute :>> mass = 0.21 [kg];
            attribute :>> cost = 46.0;
            attribute range : Real = 136.0;
            port data : Common::DataPort;
        }
        part def Controller_0736 :> Common::Component {
            attribute :>> mass = 1.10 [kg];
            attribute :>> cost = 236.0;
            port supply : Common::PowerPort;
            part sensors : Sensor_0736[2];
            action smooth : Common::Process;
            action forward : Common::Process;
            succession first smooth then forward;
            exhibit state lifecycle : Common::Lifecycle;
        }
        requirement controllerMass_0736 : Common::MassLimit {
            subject component : Controller_0736;
            attribute :>> limit = 2.0 [kg];
        }
    }

    package Subsystem_0737 {
        part def Sensor_0737 :> Common::Component {
            attribute :>> mass = 0.22 [kg];
            attribute :>> cost = 47.0;
            attribute range : Real = 137.0;
            port data : Common::DataPort;
        }
        part def Controller_0737 :> Common::Component {
            attribute :>> mass = 1.20 [kg];
            attribute :>> cost = 237.0;
            port supply : Common::PowerPort;
            part sensors : Sensor_0737[2];
            action smooth : Common::Process;
            action forward : Common::Process;
            succession first smooth then forward;
            exhibit state lifecycle : Common::Lifecycle;
        }
        requirement controllerMass_0737 : Common::MassLimit {
            subject component : Controller_0737;
            attribute :>> limit = 2.0 [kg];
        }
    }

    package Subsystem_0738 {
        part def Sensor_0738 :> Common::Component {
            attribute :>> mass = 0.23 [kg];
            attribute :>> cost = 48.0;
            attribute range : Real = 138.0;
            port data : Common::DataPort;
        }
        part def Controller_0738 :> Common::Component {
            attribute :>> mass = 1.30 [kg];
            attribute :>> cost = 238.0;
            port supply : Common::PowerPort;
            part sensors : Sensor_0738[2];
            action smooth : Common::Process;
            action forward : Common::Process;
            succession first smooth then forward;
            exhibit state lifecycle : Common::Lifecycle;
        }
        requirement controllerMass_0738 : Common::MassLimit {
            subject component : Controller_0738;
            attribute :>> limit = 2.0 [kg];
        }
    }

    package Subsystem_0739 {
        part def Sensor_0739 :> Common::Component {
            attribute :>> mass = 0.24 [kg];
            attribute :>> cost = 49.0;
            attribute range : Real = 139.0;
            port data : Common::DataPort;
        }
        part def Controller_0739 :> Common::Component {
            attribute :>> mass = 1.40 [kg];
            attribute :>> cost = 239.0;
            port supply : Common::PowerPort;
            part sensors : Sensor_0739[2];
            action smooth : Common::Process;
            action forward : Common::Process;
            succession first smooth then forward;
            exhibit state lifecycle : Common::Lifecycle;
        }
        requirement controllerMass_0739 : Common::MassLimit {
            subject component : Controller_0739;
            attribute :>> limit = 2.0 [kg];
        }
    }

    package Subsystem_0740 {
        part def Sensor_0740 :> Common::Component {
            attribute :>> mass = 0.20 [kg];
            attribute :>> cost = 30.0;
            attribute range : Real = 140.0;
            port data : Common::DataPort;
        }
        part def Controller_0740 :> Common::Component {
            attribute :>> mass = 1.50 [kg];
            attribute :>> cost = 240.0;
            port supply : Common::PowerPort;
            part sensors : Sensor_0740[2];
            action smooth : Common::Process;
            action forward : Common::Process;
            succession first smooth then forward;
            exhibit state lifecycle : Common::Lifecycle;
        }
        requirement controllerMass_0740 : Common::MassLimit {
            subject component : Controller_0740;
            attribute :>> limit = 2.0 [kg];
        }
    }

    package Subsystem_0741 {
        part def Sensor_0741 :> Common::Component {
            attribute :>> mass = 0.21 [kg];
            attribute :>> cost = 31.0;
            attribute range : Real = 141.0;
            port data : Common::DataPort;
        }
        part def Controller_0741 :> Common::Component {
            attribute :>> mass = 1.60 [kg];
            attribute :>> cost = 241.0;
            port supply : Common::PowerPort;
            part sensors : Sensor_0741[2];
            action smooth : Common::Process;
            action forward : Common::Process;
            succession first smooth then forward;
            exhibit state lifecycle : Common::Lifecycle;
        }
        requirement controllerMass_0741 : Common::MassLimit {
            subject component : Controller_0741;
            attribute :>> limit = 2.0 [kg];
        }
    }

    package Subsystem_0742 {
        part def Sensor_0742 :> Common::Component {
            attribute :>> mass = 0.22 [kg];
            attribute :>> cost = 32.0;
            attribute range : Real = 142.0;
            port data : Common::DataPort;
        }
        part def Controller_0742 :> Common::Component {
            attribute :>> mass = 1.00 [kg];
            attribute :>> cost = 242.0;
            port supply : Common::PowerPort;
            part sensors : Sensor_0742[2];
            action smooth : Common::Process;
            action forward : Common::Process;
            succession first smooth then forward;
            exhibit state lifecycle : Common::Lifecycle;
        }
        requirement controllerMass_0742 : Common::MassLimit {
            subject component : Controller_0742;
            attribute :>> limit = 2.0 [kg];
        }
    }

    package Subsystem_0743 {
        part def Sensor_0743 :> Common::Component {
            attribute :>> mass = 0.23 [kg];
            attribute :>> cost = 33.0;
            attribute range : Real = 143.0;
            port data : Common::DataPort;
        }
        part def Controller_0743 :> Common::Component {
            attribute :>> mass = 1.10 [kg];
            attribute :>> cost = 243.0;
            port supply : Common::PowerPort;
            part sensors : Sensor_0743[2];
            action smooth : Common::Process;
            action forward : Common::Process;
            succession first smooth then forward;
            exhibit state lifecycle : Common::Lifecycle;
        }
        requirement controllerMass_0743 : Common::MassLimit {
            subject component : Controller_0743;
            attribute :>> limit = 2.0 [kg];
        }
    }

    package Subsystem_0744 {
        part def Sensor_0744 :> Common::Component {
            attribute :>> mass = 0.24 [kg];
            attribute :>> cost = 34.0;
            attribute range : Real = 144.0;
            port data : Common::DataPort;
        }
        part def Controller_0744 :> Common::Component {
            attribute :>> mass = 1.20 [kg];
            attribute :>> cost = 244.0;
            port supply : Common::PowerPort;
            part sensors : Sensor_0744[2];
            action smooth : Common::Process;
            action forward : Common::Process;
            succession first smooth then forward;
            exhibit state lifecycle : Common::Lifecycle;
        }
        requirement controllerMass_0744 : Common::MassLimit {
            subject component : Controller_0744;
            attribute :>> limit = 2.0 [kg];
        }
    }

    package Subsystem_0745 {
        part def Sensor_0745 :> Common::Component {
            attribute :>> mass = 0.20 [kg];
            attribute :>> cost = 35.0;
            attribute range : Real = 145.0;
            port data : Common::DataPort;
        }
        part def Controller_0745 :> Common::Component {
            attribute :>> mass = 1.30 [kg];
            attribute :>> cost = 245.0;
            port supply : Common::PowerPort;
            part sensors : Sensor_0745[2];
            action smooth : Common::Process;
            action forward : Common::Process;
            succession first smooth then forward;
            exhibit state lifecycle : Common::Lifecycle;
        }
        requirement controllerMass_0745 : Common::MassLimit {
            subject component : Controller_0745;
            attribute :>> limit = 2.0 [kg];
        }
    }

    package Subsystem_0746 {
        part def Sensor_0746 :> Common::Component {
            attribute :>> mass = 0.21 [kg];
            attribute :>> cost = 36.0;
            attribute range : Real = 146.0;
            port data : Common::DataPort;
        }
        part def Controller_0746 :> Common::Component {
            attribute :>> mass = 1.40 [kg];
            attribute :>> cost = 246.0;
            port supply : Common::PowerPort;
            part sensors : Sensor_0746[2];
            action smooth : Common::Process;
            action forward : Common::Process;
            succession first smooth then forward;
            exhibit state lifecycle : Common::Lifecycle;
        }
        requirement controllerMass_0746 : Common::MassLimit {
            subject component : Controller_0746;
            attribute :>> limit = 2.0 [kg];
        }
    }

    package Subsystem_0747 {
        part def Sensor_0747 :> Common::Component {
            attribute :>> mass = 0.22 [kg];
            attribute :>> cost = 37.0;
            attribute range : Real = 147.0;
            port data : Common::DataPort;
        }
        part def Controller_0747 :> Common::Component {
            attribute :>> mass = 1.50 [kg];
            attribute :>> cost = 247.0;
            port supply : Common::PowerPort;
            part sensors : Sensor_0747[2];
            action smooth : Common::Process;
            action forward : Common::Process;
            succession first smooth then forward;
            exhibit state lifecycle : Common::Lifecycle;
        }
        requirement controllerMass_0747 : Common::MassLimit {
            subject component : Controller_0747;
            attribute :>> limit = 2.0 [kg];
        }
    }

    package Subsystem_0748 {
        part def Sensor_0748 :> Common::Component {
            attribute :>> mass = 0.23 [kg];
            attribute :>> cost = 38.0;
            attribute range : Real = 148.0;
            port data : Common::DataPort;
        }
        part def Controller_0748 :> Common::Component {
            attribute :>> mass = 1.60 [kg];
            attribute :>> cost = 248.0;
            port supply : Common::PowerPort;
            part sensors : Sensor_0748[2];
            action smooth : Common::Process;
            action forward : Common::Process;
            succession first smooth then forward;
            exhibit state lifecycle : Common::Lifecycle;
        }
        requirement controllerMass_0748 : Common::MassLimit {
            subject component : Controller_0748;
            attribute :>> limit = 2.0 [kg];
        }
    }

    package Subsystem_0749 {
        part def Sensor_0749 :> Common::Component {
            attribute :>> mass = 0.24 [kg];
            attribute :>> cost = 39.0;
            attribute range : Real = 149.0;
            port data : Common::DataPort;
        }
        part def Controller_0749 :> Common::Component {
            attribute :>> mass = 1.00 [kg];
            attribute :>> cost = 249.0;
            port supply : Common::PowerPort;
            part sensors : Sensor_0749[2];
            action smooth : Common::Process;
            action forward : Common::Process;
            succession first smooth then forward;
            exhibit state lifecycle : Common::Lifecycle;
        }
        requirement controllerMass_0749 : Common::MassLimit {
            subject component : Controller_0749;
            attribute :>> limit = 2.0 [kg];
        }
    }

    package Subsystem_0750 {
        part def Sensor_0750 :> Common::Component {
            attribute :>> mass = 0.20 [kg];
            attribute :>> cost = 40.0;
            attribute range : Real = 100.0;
            port data : Common::DataPort;
        }
        part def Controller_0750 :> Common::Component {
            attribute :>> mass = 1.10 [kg];
            attribute :>> cost = 250.0;
            port supply : Common::PowerPort;
            part sensors : Sensor_0750[2];
            action smooth : Common::Process;
            action forward : Common::Process;
            succession first smooth then forward;
            exhibit state lifecycle : Common::Lifecycle;
        }
        requirement controllerMass_0750 : Common::MassLimit {
            subject component : Controller_0750;
            attribute :>> limit = 2.0 [kg];
        }
    }

    package Subsystem_0751 {
        part def Sensor_0751 :> Common::Component {
            attribute :>> mass = 0.21 [kg];
            attribute :>> cost = 41.0;
            attribute range : Real = 101.0;
            port data : Common::DataPort;
        }
        part def Controller_0751 :> Common::Component {
            attribute :>> mass = 1.20 [kg];
            attribute :>> cost = 251.0;
            port supply : Common::PowerPort;
            part sensors : Sensor_0751[2];
            action smooth : Common::Process;
            action forward : Common::Process;
            succession first smooth then forward;
            exhibit state lifecycle : Common::Lifecycle;
        }
        requirement controllerMass_0751 : Common::MassLimit {
            subject component : Controller_0751;
            attribute :>> limit = 2.0 [kg];
        }
    }

    package Subsystem_0752 {
        part def Sensor_0752 :> Common::Component {
            attribute :>> mass = 0.22 [kg];
            attribute :>> cost = 42.0;
            attribute range : Real = 102.0;
            port data : Common::DataPort;
        }
        part def Controller_0752 :> Common::Component {
            attribute :>> mass = 1.30 [kg];
            attribute :>> cost = 252.0;
            port supply : Common::PowerPort;
            part sensors : Sensor_0752[2];
            action smooth : Common::Process;
            action forward : Common::Process;
            succession first smooth then forward;
            exhibit state lifecycle : Common::Lifecycle;
        }
        requirement controllerMass_0752 : Common::MassLimit {
            subject component : Controller_0752;
            attribute :>> limit = 2.0 [kg];
        }
    }

    package Subsystem_0753 {
        part def Sensor_0753 :> Common::Component {
            attribute :>> mass = 0.23 [kg];
            attribute :>> cost = 43.0;
            attribute range : Real = 103.0;
            port data : Common::DataPort;
        }
        part def Controller_0753 :> Common::Component {
            attribute :>> mass = 1.40 [kg];
            attribute :>> cost = 253.0;
            port supply : Common::PowerPort;
            part sensors : Sensor_0753[2];
            action smooth : Common::Process;
            action forward : Common::Process;
            succession first smooth then forward;
            exhibit state lifecycle : Common::Lifecycle;
        }
        requirement controllerMass_0753 : Common::MassLimit {
            subject component : Controller_0753;
            attribute :>> limit = 2.0 [kg];
        }
    }

    package Subsystem_0754 {
        part def Sensor_0754 :> Common::Component {
            attribute :>> mass = 0.24 [kg];
            attribute :>> cost = 44.0;
            attribute range : Real = 104.0;
            port data : Common::DataPort;
        }
        part def Controller_0754 :> Common::Component {
            attribute :>> mass = 1.50 [kg];
            attribute :>> cost = 254.0;
            port supply : Common::PowerPort;
            part sensors : Sensor_0754[2];
            action smooth : Common::Process;
            action forward : Common::Process;
            succession first smooth then forward;
            exhibit state lifecycle : Common::Lifecycle;
        }
        requirement controllerMass_0754 : Common::MassLimit {
            subject component : Controller_0754;
            attribute :>> limit = 2.0 [kg];
        }
    }

    package Subsystem_0755 {
        part def Sensor_0755 :> Common::Component {
            attribute :>> mass = 0.20 [kg];
            attribute :>> cost = 45.0;
            attribute range : Real = 105.0;
            port data : Common::DataPort;
        }
        part def Controller_0755 :> Common::Component {
            attribute :>> mass = 1.60 [kg];
            attribute :>> cost = 255.0;
            port supply : Common::PowerPort;
            part sensors : Sensor_0755[2];
            action smooth : Common::Process;
            action forward : Common::Process;
            succession first smooth then forward;
            exhibit state lifecycle : Common::Lifecycle;
        }
        requirement controllerMass_0755 : Common::MassLimit {
            subject component : Controller_0755;
            attribute :>> limit = 2.0 [kg];
        }
    }

    package Subsystem_0756 {
        part def Sensor_0756 :> Common::Component {
            attribute :>> mass = 0.21 [kg];
            attribute :>> cost = 46.0;
            attribute range : Real = 106.0;
            port data : Common::DataPort;
        }
        part def Controller_0756 :> Common::Component {
            attribute :>> mass = 1.00 [kg];
            attribute :>> cost = 256.0;
            port supply : Common::PowerPort;
            part sensors : Sensor_0756[2];
            action smooth : Common::Process;
            action forward : Common::Process;
            succession first smooth then forward;
            exhibit state lifecycle : Common::Lifecycle;
        }
        requirement controllerMass_0756 : Common::MassLimit {
            subject component : Controller_0756;
            attribute :>> limit = 2.0 [kg];
        }
    }

    package Subsystem_0757 {
        part def Sensor_0757 :> Common::Component {
            attribute :>> mass = 0.22 [kg];
            attribute :>> cost = 47.0;
            attribute range : Real = 107.0;
            port data : Common::DataPort;
        }
        part def Controller_0757 :> Common::Component {
            attribute :>> mass = 1.10 [kg];
            attribute :>> cost = 257.0;
            port supply : Common::PowerPort;
            part sensors : Sensor_0757[2];
            action smooth : Common::Process;
            action forward : Common::Process;
            succession first smooth then forward;
            exhibit state lifecycle : Common::Lifecycle;
        }
        requirement controllerMass_0757 : Common::MassLimit {
            subject component : Controller_0757;
            attribute :>> limit = 2.0 [kg];
        }
    }

    package Subsystem_0758 {
        part def Sensor_0758 :> Common::Component {
            attribute :>> mass = 0.23 [kg];
            attribute :>> cost = 48.0;
            attribute range : Real = 108.0;
            port data : Common::DataPort;
        }
        part def Controller_0758 :> Common::Component {
            attribute :>> mass = 1.20 [kg];
            attribute :>> cost = 258.0;
            port supply : Common::PowerPort;
            part sensors : Sensor_0758[2];
            action smooth : Common::Process;
            action forward : Common::Process;
            succession first smooth then forward;
            exhibit state lifecycle : Common::Lifecycle;
        }
        requirement controllerMass_0758 : Common::MassLimit {
            subject component : Controller_0758;
            attribute :>> limit = 2.0 [kg];
        }
    }

    package Subsystem_0759 {
        part def Sensor_0759 :> Common::Component {
            attribute :>> mass = 0.24 [kg];
            attribute :>> cost = 49.0;
            attribute range : Real = 109.0;
            port data : Common::DataPort;
        }
        part def Controller_0759 :> Common::Component {
            attribute :>> mass = 1.30 [kg];
            attribute :>> cost = 259.0;
            port supply : Common::PowerPort;
            part sensors : Sensor_0759[2];
            action smooth : Common::Process;
            action forward : Common::Process;
            succession first smooth then forward;
            exhibit state lifecycle : Common::Lifecycle;
        }
        requirement controllerMass_0759 : Common::MassLimit {
            subject component : Controller_0759;
            attribute :>> limit = 2.0 [kg];
        }
    }

    package Subsystem_0760 {
        part def Sensor_0760 :> Common::Component {
            attribute :>> mass = 0.20 [kg];
            attribute :>> cost = 30.0;
            attribute range : Real = 110.0;
            port data : Common::DataPort;
        }
        part def Controller_0760 :> Common::Component {
            attribute :>> mass = 1.40 [kg];
            attribute :>> cost = 260.0;
            port supply : Common::PowerPort;
            part sensors : Sensor_0760[2];
            action smooth : Common::Process;
            action forward : Common::Process;
            succession first smooth then forward;
            exhibit state lifecycle : Common::Lifecycle;
        }
        requirement controllerMass_0760 : Common::MassLimit {
            subject component : Controller_0760;
            attribute :>> limit = 2.0 [kg];
        }
    }

    package Subsystem_0761 {
        part def Sensor_0761 :> Common::Component {
            attribute :>> mass = 0.21 [kg];
            attribute :>> cost = 31.0;
            attribute range : Real = 111.0;
            port data : Common::DataPort;
        }
        part def Controller_0761 :> Common::Component {
            attribute :>> mass = 1.50 [kg];
            attribute :>> cost = 261.0;
            port supply : Common::PowerPort;
            part sensors : Sensor_0761[2];
            action smooth : Common::Process;
            action forward : Common::Process;
            succession first smooth then forward;
            exhibit state lifecycle : Common::Lifecycle;
        }
        requirement controllerMass_0761 : Common::MassLimit {
            subject component : Controller_0761;
            attribute :>> limit = 2.0 [kg];
        }
    }

    package Subsystem_0762 {
        part def Sensor_0762 :> Common::Component {
            attribute :>> mass = 0.22 [kg];
            attribute :>> cost = 32.0;
            attribute range : Real = 112.0;
            port data : Common::DataPort;
        }
        part def Controller_0762 :> Common::Component {
            attribute :>> mass = 1.60 [kg];
            attribute :>> cost = 262.0;
            port supply : Common::PowerPort;
            part sensors : Sensor_0762[2];
            action smooth : Common::Process;
            action forward : Common::Process;
            succession first smooth then forward;
            exhibit state lifecycle : Common::Lifecycle;
        }
        requirement controllerMass_0762 : Common::MassLimit {
            subject component : Controller_0762;
            attribute :>> limit = 2.0 [kg];
        }
    }

    package Subsystem_0763 {
        part def Sensor_0763 :> Common::Component {
            attribute :>> mass = 0.23 [kg];
            attribute :>> cost = 33.0;
            attribute range : Real = 113.0;
            port data : Common::DataPort;
        }
        part def Controller_0763 :> Common::Component {
            attribute :>> mass = 1.00 [kg];
            attribute :>> cost = 263.0;
            port supply : Common::PowerPort;
            part sensors : Sensor_0763[2];
            action smooth : Common::Process;
            action forward : Common::Process;
            succession first smooth then forward;
            exhibit state lifecycle : Common::Lifecycle;
        }
        requirement controllerMass_0763 : Common::MassLimit {
            subject component : Controller_0763;
            attribute :>> limit = 2.0 [kg];
        }
    }

    package Subsystem_0764 {
        part def Sensor_0764 :> Common::Component {
            attribute :>> mass = 0.24 [kg];
            attribute :>> cost = 34.0;
            attribute range : Real = 114.0;
            port data : Common::DataPort;
        }
        part def Controller_0764 :> Common::Component {
            attribute :>> mass = 1.10 [kg];
            attribute :>> cost = 264.0;
            port supply : Common::PowerPort;
            part sensors : Sensor_0764[2];
            action smooth : Common::Process;
            action forward : Common::Process;
            succession first smooth then forward;
            exhibit state lifecycle : Common::Lifecycle;
        }
        requirement controllerMass_0764 : Common::MassLimit {
            subject component : Controller_0764;
            attribute :>> limit = 2.0 [kg];
        }
    }

    package Subsystem_0765 {
        part def Sensor_0765 :> Common::Component {
            attribute :>> mass = 0.20 [kg];
            attribute :>> cost = 35.0;
            attribute range : Real = 115.0;
            port data : Common::DataPort;
        }
        part def Controller_0765 :> Common::Component {
            attribute :>> mass = 1.20 [kg];
            attribute :>> cost = 265.0;
            port supply : Common::PowerPort;
            part sensors : Sensor_0765[2];
            action smooth : Common::Process;
            action forward : Common::Process;
            succession first smooth then forward;
            exhibit state lifecycle : Common::Lifecycle;
        }
        requirement controllerMass_0765 : Common::MassLimit {
            subject component : Controller_0765;
            attribute :>> limit = 2.0 [kg];
        }
    }

    package Subsystem_0766 {
        part def Sensor_0766 :> Common::Component {
            attribute :>> mass = 0.21 [kg];
            attribute :>> cost = 36.0;
            attribute range : Real = 116.0;
            port data : Common::DataPort;
        }
        part def Controller_0766 :> Common::Component {
            attribute :>> mass = 1.30 [kg];
            attribute :>> cost = 266.0;
            port supply : Common::PowerPort;
            part sensors : Sensor_0766[2];
            action smooth : Common::Process;
            action forward : Common::Process;
            succession first smooth then forward;
            exhibit state lifecycle : Common::Lifecycle;
        }
        requirement controllerMass_0766 : Common::MassLimit {
            subject component : Controller_0766;
            attribute :>> limit = 2.0 [kg];
        }
    }

    package Subsystem_0767 {
        part def Sensor_0767 :> Common::Component {
            attribute :>> mass = 0.22 [kg];
            attribute :>> cost = 37.0;
            attribute range : Real = 117.0;
            port data : Common::DataPort;
        }
        part def Controller_0767 :> Common::Component {
            attribute :>> mass = 1.40 [kg];
            attribute :>> cost = 267.0;
            port supply : Common::PowerPort;
            part sensors : Sensor_0767[2];
            action smooth : Common::Process;
            action forward : Common::Process;
            succession first smooth then forward;
            exhibit state lifecycle : Common::Lifecycle;
        }
        requirement controllerMass_0767 : Common::MassLimit {
            subject component : Controller_0767;
            attribute :>> limit = 2.0 [kg];
        }
    }

    package Subsystem_0768 {
        part def Sensor_0768 :> Common::Component {
            attribute :>> mass = 0.23 [kg];
            attribute :>> cost = 38.0;
            attribute range : Real = 118.0;
            port data : Common::DataPort;
        }
        part def Controller_0768 :> Common::Component {
            attribute :>> mass = 1.50 [kg];
            attribute :>> cost = 268.0;
            port supply : Common::PowerPort;
            part sensors : Sensor_0768[2];
            action smooth : Common::Process;
            action forward : Common::Process;
            succession first smooth then forward;
            exhibit state lifecycle : Common::Lifecycle;
        }
        requirement controllerMass_0768 : Common::MassLimit {
            subject component : Controller_0768;
            attribute :>> limit = 2.0 [kg];
        }
    }

    package Subsystem_0769 {
        part def Sensor_0769 :> Common::Component {
            attribute :>> mass = 0.24 [kg];
            attribute :>> cost = 39.0;
            attribute range : Real = 119.0;
            port data : Common::DataPort;
        }
        part def Controller_0769 :> Common::Component {
            attribute :>> mass = 1.60 [kg];
            attribute :>> cost = 269.0;
            port supply : Common::PowerPort;
            part sensors : Sensor_0769[2];
            action smooth : Common::Process;
            action forward : Common::Process;
            succession first smooth then forward;
            exhibit state lifecycle : Common::Lifecycle;
        }
        requirement controllerMass_0769 : Common::MassLimit {
            subject component : Controller_0769;
            attribute :>> limit = 2.0 [kg];
        }
    }

    package Subsystem_0770 {
        part def Sensor_0770 :> Common::Component {
            attribute :>> mass = 0.20 [kg];
            attribute :>> cost = 40.0;
            attribute range : Real = 120.0;
            port data : Common::DataPort;
        }
        part def Controller_0770 :> Common::Component {
            attribute :>> mass = 1.00 [kg];
            attribute :>> cost = 270.0;
            port supply : Common::PowerPort;
            part sensors : Sensor_0770[2];
            action smooth : Common::Process;
            action forward : Common::Process;
            succession first smooth then forward;
            exhibit state lifecycle : Common::Lifecycle;
        }
        requirement controllerMass_0770 : Common::MassLimit {
            subject component : Controller_0770;
            attribute :>> limit = 2.0 [kg];
        }
    }

    package Subsystem_0771 {
        part def Sensor_0771 :> Common::Component {
            attribute :>> mass = 0.21 [kg];
            attribute :>> cost = 41.0;
            attribute range : Real = 121.0;
            port data : Common::DataPort;
        }
        part def Controller_0771 :> Common::Component {
            attribute :>> mass = 1.10 [kg];
            attribute :>> cost = 271.0;
            port supply : Common::PowerPort;
            part sensors : Sensor_0771[2];
            action smooth : Common::Process;
            action forward : Common::Process;
            succession first smooth then forward;
            exhibit state lifecycle : Common::Lifecycle;
        }
        requirement controllerMass_0771 : Common::MassLimit {
            subject component : Controller_0771;
            attribute :>> limit = 2.0 [kg];
        }
    }

    package Subsystem_0772 {
        part def Sensor_0772 :> Common::Component {
            attribute :>> mass = 0.22 [kg];
            attribute :>> cost = 42.0;
            attribute range : Real = 122.0;
            port data : Common::DataPort;
        }
        part def Controller_0772 :> Common::Component {
            attribute :>> mass = 1.20 [kg];
            attribute :>> cost = 272.0;
            port supply : Common::PowerPort;
            part sensors : Sensor_0772[2];
            action smooth : Common::Process;
            action forward : Common::Process;
            succession first smooth then forward;
            exhibit state lifecycle : Common::Lifecycle;
        }
        requirement controllerMass_0772 : Common::MassLimit {
            subject component : Controller_0772;
            attribute :>> limit = 2.0 [kg];
        }
    }

    package Subsystem_0773 {
        part def Sensor_0773 :> Common::Component {
            attribute :>> mass = 0.23 [kg];
            attribute :>> cost = 43.0;
            attribute range : Real = 123.0;
            port data : Common::DataPort;
        }
        part def Controller_0773 :> Common::Component {
            attribute :>> mass = 1.30 [kg];
            attribute :>> cost = 273.0;
            port supply : Common::PowerPort;
            part sensors : Sensor_0773[2];
            action smooth : Common::Process;
            action forward : Common::Process;
            succession first smooth then forward;
            exhibit state lifecycle : Common::Lifecycle;
        }
        requirement controllerMass_0773 : Common::MassLimit {
            subject component : Controller_0773;
            attribute :>> limit = 2.0 [kg];
        }
    }

    package Subsystem_0774 {
        part def Sensor_0774 :> Common::Component {
            attribute :>> mass = 0.24 [kg];
            attribute :>> cost = 44.0;
            attribute range : Real = 124.0;
            port data : Common::DataPort;
        }
        part def Controller_0774 :> Common::Component {
            attribute :>> mass = 1.40 [kg];
            attribute :>> cost = 274.0;
            port supply : Common::PowerPort;
            part sensors : Sensor_0774[2];
            action smooth : Common::Process;
            action forward : Common::Process;
            succession first smooth then forward;
            exhibit state lifecycle : Common::Lifecycle;
        }
        requirement controllerMass_0774 : Common::MassLimit {
            subject component : Controller_0774;
            attribute :>> limit = 2.0 [kg];
        }
    }

    package Subsystem_0775 {
        part def Sensor_0775 :> Common::Component {
            attribute :>> mass = 0.20 [kg];
            attribute :>> cost = 45.0;
            attribute range : Real = 125.0;
            port data : Common::DataPort;
        }
        part def Controller_0775 :> Common::Component {
            attribute :>> mass = 1.50 [kg];
            attribute :>> cost = 275.0;
            port supply : Common::PowerPort;
            part sensors : Sensor_0775[2];
            action smooth : Common::Process;
            action forward : Common::Process;
            succession first smooth then forward;
            exhibit state lifecycle : Common::Lifecycle;
        }
        requirement controllerMass_0775 : Common::MassLimit {
            subject component : Controller_0775;
            attribute :>> limit = 2.0 [kg];
        }
    }

    package Subsystem_0776 {
        part def Sensor_0776 :> Common::Component {
            attribute :>> mass = 0.21 [kg];
            attribute :>> cost = 46.0;
            attribute range : Real = 126.0;
            port data : Common::DataPort;
        }
        part def Controller_0776 :> Common::Component {
            attribute :>> mass = 1.60 [kg];
            attribute :>> cost = 276.0;
            port supply : Common::PowerPort;
            part sensors : Sensor_0776[2];
            action smooth : Common::Process;
            action forward : Common::Process;
            succession first smooth then forward;
            exhibit state lifecycle : Common::Lifecycle;
        }
        requirement controllerMass_0776 : Common::MassLimit {
            subject component : Controller_0776;
            attribute :>> limit = 2.0 [kg];
        }
    }

    package Subsystem_0777 {
        part def Sensor_0777 :> Common::Component {
            attribute :>> mass = 0.22 [kg];
            attribute :>> cost = 47.0;
            attribute range : Real = 127.0;
            port data : Common::DataPort;
        }
        part def Controller_0777 :> Common::Component {
            attribute :>> mass = 1.00 [kg];
            attribute :>> cost = 277.0;
            port supply : Common::PowerPort;
            part sensors : Sensor_0777[2];
            action smooth : Common::Process;
            action forward : Common::Process;
            succession first smooth then forward;
            exhibit state lifecycle : Common::Lifecycle;
        }
        requirement controllerMass_0777 : Common::MassLimit {
            subject component : Controller_0777;
            attribute :>> limit = 2.0 [kg];
        }
    }

    package Subsystem_0778 {
        part def Sensor_0778 :> Common::Component {
            attribute :>> mass = 0.23 [kg];
            attribute :>> cost = 48.0;
            attribute range : Real = 128.0;
            port data : Common::DataPort;
        }
        part def Controller_0778 :> Common::Component {
            attribute :>> mass = 1.10 [kg];
            attribute :>> cost = 278.0;
            port supply : Common::PowerPort;
            part sensors : Sensor_0778[2];
            action smooth : Common::Process;
            action forward : Common::Process;
            succession first smooth then forward;
            exhibit state lifecycle : Common::Lifecycle;
        }
        requirement controllerMass_0778 : Common::MassLimit {
            subject component : Controller_0778;
            attribute :>> limit = 2.0 [kg];
        }
    }

    package Subsystem_0779 {
        part def Sensor_0779 :> Common::Component {
            attribute :>> mass = 0.24 [kg];
            attribute :>> cost = 49.0;
            attribute range : Real = 129.0;
            port data : Common::DataPort;
        }
        part def Controller_0779 :> Common::Component {
            attribute :>> mass = 1.20 [kg];
            attribute :>> cost = 279.0;
            port supply : Common::PowerPort;
            part sensors : Sensor_0779[2];
            action smooth : Common::Process;
            action forward : Common::Process;
            succession first smooth then forward;
            exhibit state lifecycle : Common::Lifecycle;
        }
        requirement controllerMass_0779 : Common::MassLimit {
            subject component : Controller_0779;
            attribute :>> limit = 2.0 [kg];
        }
    }

    package Subsystem_0780 {
        part def Sensor_0780 :> Common::Component {
            attribute :>> mass = 0.20 [kg];
            attribute :>> cost = 30.0;
            attribute range : Real = 130.0;
            port data : Common::DataPort;
        }
        part def Controller_0780 :> Common::Component {
            attribute :>> mass = 1.30 [kg];
            attribute :>> cost = 280.0;
            port supply : Common::PowerPort;
            part sensors : Sensor_0780[2];
            action smooth : Common::Process;
            action forward : Common::Process;
            succession first smooth then forward;
            exhibit state lifecycle : Common::Lifecycle;
        }
        requirement controllerMass_0780 : Common::MassLimit {
            subject component : Controller_0780;
            attribute :>> limit = 2.0 [kg];
        }
    }

    package Subsystem_0781 {
        part def Sensor_0781 :> Common::Component {
            attribute :>> mass = 0.21 [kg];
            attribute :>> cost = 31.0;
            attribute range : Real = 131.0;
            port data : Common::DataPort;
        }
        part def Controller_0781 :> Common::Component {
            attribute :>> mass = 1.40 [kg];
            attribute :>> cost = 281.0;
            port supply : Common::PowerPort;
            part sensors : Sensor_0781[2];
            action smooth : Common::Process;
            action forward : Common::Process;
            succession first smooth then forward;
            exhibit state lifecycle : Common::Lifecycle;
        }
        requirement controllerMass_0781 : Common::MassLimit {
            subject component : Controller_0781;
            attribute :>> limit = 2.0 [kg];
        }
    }

    package Subsystem_0782 {
        part def Sensor_0782 :> Common::Component {
            attribute :>> mass = 0.22 [kg];
            attribute :>> cost = 32.0;
            attribute range : Real = 132.0;
            port data : Common::DataPort;
        }
        part def Controller_0782 :> Common::Component {
            attribute :>> mass = 1.50 [kg];
            attribute :>> cost = 282.0;
            port supply : Common::PowerPort;
            part sensors : Sensor_0782[2];
            action smooth : Common::Process;
            action forward : Common::Process;
            succession first smooth then forward;
            exhibit state lifecycle : Common::Lifecycle;
        }
        requirement controllerMass_0782 : Common::MassLimit {
            subject component : Controller_0782;
            attribute :>> limit = 2.0 [kg];
        }
    }

    package Subsystem_0783 {
        part def Sensor_0783 :> Common::Component {
            attribute :>> mass = 0.23 [kg];
            attribute :>> cost = 33.0;
            attribute range : Real = 133.0;
            port data : Common::DataPort;
        }
        part def Controller_0783 :> Common::Component {
            attribute :>> mass = 1.60 [kg];
            attribute :>> cost = 283.0;
            port supply : Common::PowerPort;
            part sensors : Sensor_0783[2];
            action smooth : Common::Process;
            action forward : Common::Process;
            succession first smooth then forward;
            exhibit state lifecycle : Common::Lifecycle;
        }
        requirement controllerMass_0783 : Common::MassLimit {
            subject component : Controller_0783;
            attribute :>> limit = 2.0 [kg];
        }
    }

    package Subsystem_0784 {
        part def Sensor_0784 :> Common::Component {
            attribute :>> mass = 0.24 [kg];
            attribute :>> cost = 34.0;
            attribute range : Real = 134.0;
            port data : Common::DataPort;
        }
        part def Controller_0784 :> Common::Component {
            attribute :>> mass = 1.00 [kg];
            attribute :>> cost = 284.0;
            port supply : Common::PowerPort;
            part sensors : Sensor_0784[2];
            action smooth : Common::Process;
            action forward : Common::Process;
            succession first smooth then forward;
            exhibit state lifecycle : Common::Lifecycle;
        }
        requirement controllerMass_0784 : Common::MassLimit {
            subject component : Controller_0784;
            attribute :>> limit = 2.0 [kg];
        }
    }

    package Subsystem_0785 {
        part def Sensor_0785 :> Common::Component {
            attribute :>> mass = 0.20 [kg];
            attribute :>> cost = 35.0;
            attribute range : Real = 135.0;
            port data : Common::DataPort;
        }
        part def Controller_0785 :> Common::Component {
            attribute :>> mass = 1.10 [kg];
            attribute :>> cost = 285.0;
            port supply : Common::PowerPort;
            part sensors : Sensor_0785[2];
            action smooth : Common::Process;
            action forward : Common::Process;
            succession first smooth then forward;
            exhibit state lifecycle : Common::Lifecycle;
        }
        requirement controllerMass_0785 : Common::MassLimit {
            subject component : Controller_0785;
            attribute :>> limit = 2.0 [kg];
        }
    }

    package Subsystem_0786 {
        part def Sensor_0786 :> Common::Component {
            attribute :>> mass = 0.21 [kg];
            attribute :>> cost = 36.0;
            attribute range : Real = 136.0;
            port data : Common::DataPort;
        }
        part def Controller_0786 :> Common::Component {
            attribute :>> mass = 1.20 [kg];
            attribute :>> cost = 286.0;
            port supply : Common::PowerPort;
            part sensors : Sensor_0786[2];
            action smooth : Common::Process;
            action forward : Common::Process;
            succession first smooth then forward;
            exhibit state lifecycle : Common::Lifecycle;
        }
        requirement controllerMass_0786 : Common::MassLimit {
            subject component : Controller_0786;
            attribute :>> limit = 2.0 [kg];
        }
    }

    package Subsystem_0787 {
        part def Sensor_0787 :> Common::Component {
            attribute :>> mass = 0.22 [kg];
            attribute :>> cost = 37.0;
            attribute range : Real = 137.0;
            port data : Common::DataPort;
        }
        part def Controller_0787 :> Common::Component {
            attribute :>> mass = 1.30 [kg];
            attribute :>> cost = 287.0;
            port supply : Common::PowerPort;
            part sensors : Sensor_0787[2];
            action smooth : Common::Process;
            action forward : Common::Process;
            succession first smooth then forward;
            exhibit state lifecycle : Common::Lifecycle;
        }
        requirement controllerMass_0787 : Common::MassLimit {
            subject component : Controller_0787;
            attribute :>> limit = 2.0 [kg];
        }
    }

    package Subsystem_0788 {
        part def Sensor_0788 :> Common::Component {
            attribute :>> mass = 0.23 [kg];
            attribute :>> cost = 38.0;
            attribute range : Real = 138.0;
            port data : Common::DataPort;
        }
        part def Controller_0788 :> Common::Component {
            attribute :>> mass = 1.40 [kg];
            attribute :>> cost = 288.0;
            port supply : Common::PowerPort;
            part sensors : Sensor_0788[2];
            action smooth : Common::Process;
            action forward : Common::Process;
            succession first smooth then forward;
            exhibit state lifecycle : Common::Lifecycle;
        }
        requirement controllerMass_0788 : Common::MassLimit {
            subject component : Controller_0788;
            attribute :>> limit = 2.0 [kg];
        }
    }

    package Subsystem_0789 {
        part def Sensor_0789 :> Common::Component {
            attribute :>> mass = 0.24 [kg];
            attribute :>> cost = 39.0;
            attribute range : Real = 139.0;
            port data : Common::DataPort;
        }
        part def Controller_0789 :> Common::Component {
            attribute :>> mass = 1.50 [kg];
            attribute :>> cost = 289.0;
            port supply : Common::PowerPort;
            part sensors : Sensor_0789[2];
            action smooth : Common::Process;
            action forward : Common::Process;
            succession first smooth then forward;
            exhibit state lifecycle : Common::Lifecycle;
        }
        requirement controllerMass_0789 : Common::MassLimit {
            subject component : Controller_0789;
            attribute :>> limit = 2.0 [kg];
        }
    }

    package Subsystem_0790 {
        part def Sensor_0790 :> Common::Component {
            attribute :>> mass = 0.20 [kg];
            attribute :>> cost = 40.0;
            attribute range : Real = 140.0;
            port data : Common::DataPort;
        }
        part def Controller_0790 :> Common::Component {
            attribute :>> mass = 1.60 [kg];
            attribute :>> cost = 290.0;
            port supply : Common::PowerPort;
            part sensors : Sensor_0790[2];
            action smooth : Common::Process;
            action forward : Common::Process;
            succession first smooth then forward;
            exhibit state lifecycle : Common::Lifecycle;
        }
        requirement controllerMass_0790 : Common::MassLimit {
            subject component : Controller_0790;
            attribute :>> limit = 2.0 [kg];
        }
    }

    package Subsystem_0791 {
        part def Sensor_0791 :> Common::Component {
            attribute :>> mass = 0.21 [kg];
            attribute :>> cost = 41.0;
            attribute range : Real = 141.0;
            port data : Common::DataPort;
        }
        part def Controller_0791 :> Common::Component {
            attribute :>> mass = 1.00 [kg];
            attribute :>> cost = 291.0;
            port supply : Common::PowerPort;
            part sensors : Sensor_0791[2];
            action smooth : Common::Process;
            action forward : Common::Process;
            succession first smooth then forward;
            exhibit state lifecycle : Common::Lifecycle;
        }
        requirement controllerMass_0791 : Common::MassLimit {
            subject component : Controller_0791;
            attribute :>> limit = 2.0 [kg];
        }
    }

    package Subsystem_0792 {
        part def Sensor_0792 :> Common::Component {
            attribute :>> mass = 0.22 [kg];
            attribute :>> cost = 42.0;
            attribute range : Real = 142.0;
            port data : Common::DataPort;
        }
        part def Controller_0792 :> Common::Component {
            attribute :>> mass = 1.10 [kg];
            attribute :>> cost = 292.0;
            port supply : Common::PowerPort;
            part sensors : Sensor_0792[2];
            action smooth : Common::Process;
            action forward : Common::Process;
            succession first smooth then forward;
            exhibit state lifecycle : Common::Lifecycle;
        }
        requirement controllerMass_0792 : Common::MassLimit {
            subject component : Controller_0792;
            attribute :>> limit = 2.0 [kg];
        }
    }

    package Subsystem_0793 {
        part def Sensor_0793 :> Common::Component {
            attribute :>> mass = 0.23 [kg];
            attribute :>> cost = 43.0;
            attribute range : Real = 143.0;
            port data : Common::DataPort;
        }
        part def Controller_0793 :> Common::Component {
            attribute :>> mass = 1.20 [kg];
            attribute :>> cost = 293.0;
            port supply : Common::PowerPort;
            part sensors : Sensor_0793[2];
            action smooth : Common::Process;
            action forward : Common::Process;
            succession first smooth then forward;
            exhibit state lifecycle : Common::Lifecycle;
        }
        requirement controllerMass_0793 : Common::MassLimit {
            subject component : Controller_0793;
            attribute :>> limit = 2.0 [kg];
        }
    }

    package Subsystem_0794 {
        part def Sensor_0794 :> Common::Component {
            attribute :>> mass = 0.24 [kg];
            attribute :>> cost = 44.0;
            attribute range : Real = 144.0;
            port data : Common::DataPort;
        }
        part def Controller_0794 :> Common::Component {
            attribute :>> mass = 1.30 [kg];
            attribute :>> cost = 294.0;
            port supply : Common::PowerPort;
            part sensors : Sensor_0794[2];
            action smooth : Common::Process;
            action forward : Common::Process;
            succession first smooth then forward;
            exhibit state lifecycle : Common::Lifecycle;
        }
        requirement controllerMass_0794 : Common::MassLimit {
            subject component : Controller_0794;
            attribute :>> limit = 2.0 [kg];
        }
    }

    package Subsystem_0795 {
        part def Sensor_0795 :> Common::Component {
            attribute :>> mass = 0.20 [kg];
            attribute :>> cost = 45.0;
            attribute range : Real = 145.0;
            port data : Common::DataPort;
        }
        part def Controller_0795 :> Common::Component {
            attribute :>> mass = 1.40 [kg];
            attribute :>> cost = 295.0;
            port supply : Common::PowerPort;
            part sensors : Sensor_0795[2];
            action smooth : Common::Process;
            action forward : Common::Process;
            succession first smooth then forward;
            exhibit state lifecycle : Common::Lifecycle;
        }
        requirement controllerMass_0795 : Common::MassLimit {
            subject component : Controller_0795;
            attribute :>> limit = 2.0 [kg];
        }
    }

    package Subsystem_0796 {
        part def Sensor_0796 :> Common::Component {
            attribute :>> mass = 0.21 [kg];
            attribute :>> cost = 46.0;
            attribute range : Real = 146.0;
            port data : Common::DataPort;
        }
        part def Controller_0796 :> Common::Component {
            attribute :>> mass = 1.50 [kg];
            attribute :>> cost = 296.0;
            port supply : Common::PowerPort;
            part sensors : Sensor_0796[2];
            action smooth : Common::Process;
            action forward : Common::Process;
            succession first smooth then forward;
            exhibit state lifecycle : Common::Lifecycle;
        }
        requirement controllerMass_0796 : Common::MassLimit {
            subject component : Controller_0796;
            attribute :>> limit = 2.0 [kg];
        }
    }

    package Subsystem_0797 {
        part def Sensor_0797 :> Common::Component {
            attribute :>> mass = 0.22 [kg];
            attribute :>> cost = 47.0;
            attribute range : Real = 147.0;
            port data : Common::DataPort;
        }
        part def Controller_0797 :> Common::Component {
            attribute :>> mass = 1.60 [kg];
            attribute :>> cost = 297.0;
            port supply : Common::PowerPort;
            part sensors : Sensor_0797[2];
            action smooth : Common::Process;
            action forward : Common::Process;
            succession first smooth then forward;
            exhibit state lifecycle : Common::Lifecycle;
        }
        requirement controllerMass_0797 : Common::MassLimit {
            subject component : Controller_0797;
            attribute :>> limit = 2.0 [kg];
        }
    }

    package Subsystem_0798 {
        part def Sensor_0798 :> Common::Component {
            attribute :>> mass = 0.23 [kg];
            attribute :>> cost = 48.0;
            attribute range : Real = 148.0;
            port data : Common::DataPort;
        }
        part def Controller_0798 :> Common::Component {
            attribute :>> mass = 1.00 [kg];
            attribute :>> cost = 298.0;
            port supply : Common::PowerPort;
            part sensors : Sensor_0798[2];
            action smooth : Common::Process;
            action forward : Common::Process;
            succession first smooth then forward;
            exhibit state lifecycle : Common::Lifecycle;
        }
        requirement controllerMass_0798 : Common::MassLimit {
            subject component : Controller_0798;
            attribute :>> limit = 2.0 [kg];
        }
    }

    package Subsystem_0799 {
        part def Sensor_0799 :> Common::Component {
            attribute :>> mass = 0.24 [kg];
            attribute :>> cost = 49.0;
            attribute range : Real = 149.0;
            port data : Common::DataPort;
        }
        part def Controller_0799 :> Common::Component {
            attribute :>> mass = 1.10 [kg];
            attribute :>> cost = 299.0;
            port supply : Common::PowerPort;
            part sensors : Sensor_0799[2];
            action smooth : Common::Process;
            action forward : Common::Process;
            succession first smooth then forward;
            exhibit state lifecycle : Common::Lifecycle;
        }
        requirement controllerMass_0799 : Common::MassLimit {
            subject component : Controller_0799;
            attribute :>> limit = 2.0 [kg];
        }
    }

    package Subsystem_0800 {
        part def Sensor_0800 :> Common::Component {
            attribute :>> mass = 0.20 [kg];
            attribute :>> cost = 30.0;
            attribute range : Real = 100.0;
            port data : Common::DataPort;
        }
        part def Controller_0800 :> Common::Component {
            attribute :>> mass = 1.20 [kg];
            attribute :>> cost = 200.0;
            port supply : Common::PowerPort;
            part sensors : Sensor_0800[2];
            action smooth : Common::Process;
            action forward : Common::Process;
            succession first smooth then forward;
            exhibit state lifecycle : Common::Lifecycle;
        }
        requirement controllerMass_0800 : Common::MassLimit {
            subject component : Controller_0800;
            attribute :>> limit = 2.0 [kg];
        }
    }

    package Subsystem_0801 {
        part def Sensor_0801 :> Common::Component {
            attribute :>> mass = 0.21 [kg];
            attribute :>> cost = 31.0;
            attribute range : Real = 101.0;
            port data : Common::DataPort;
        }
        part def Controller_0801 :> Common::Component {
            attribute :>> mass = 1.30 [kg];
            attribute :>> cost = 201.0;
            port supply : Common::PowerPort;
            part sensors : Sensor_0801[2];
            action smooth : Common::Process;
            action forward : Common::Process;
            succession first smooth then forward;
            exhibit state lifecycle : Common::Lifecycle;
        }
        requirement controllerMass_0801 : Common::MassLimit {
            subject component : Controller_0801;
            attribute :>> limit = 2.0 [kg];
        }
    }

    package Subsystem_0802 {
        part def Sensor_0802 :> Common::Component {
            attribute :>> mass = 0.22 [kg];
            attribute :>> cost = 32.0;
            attribute range : Real = 102.0;
            port data : Common::DataPort;
        }
        part def Controller_0802 :> Common::Component {
            attribute :>> mass = 1.40 [kg];
            attribute :>> cost = 202.0;
            port supply : Common::PowerPort;
            part sensors : Sensor_0802[2];
            action smooth : Common::Process;
            action forward : Common::Process;
            succession first smooth then forward;
            exhibit state lifecycle : Common::Lifecycle;
        }
        requirement controllerMass_0802 : Common::MassLimit {
            subject component : Controller_0802;
            attribute :>> limit = 2.0 [kg];
        }
    }

    package Subsystem_0803 {
        part def Sensor_0803 :> Common::Component {
            attribute :>> mass = 0.23 [kg];
            attribute :>> cost = 33.0;
            attribute range : Real = 103.0;
            port data : Common::DataPort;
        }
        part def Controller_0803 :> Common::Component {
            attribute :>> mass = 1.50 [kg];
            attribute :>> cost = 203.0;
            port supply : Common::PowerPort;
            part sensors : Sensor_0803[2];
            action smooth : Common::Process;
            action forward : Common::Process;
            succession first smooth then forward;
            exhibit state lifecycle : Common::Lifecycle;
        }
        requirement controllerMass_0803 : Common::MassLimit {
            subject component : Controller_0803;
            attribute :>> limit = 2.0 [kg];
        }
    }

    package Subsystem_0804 {
        part def Sensor_0804 :> Common::Component {
            attribute :>> mass = 0.24 [kg];
            attribute :>> cost = 34.0;
            attribute range : Real = 104.0;
            port data : Common::DataPort;
        }
        part def Controller_0804 :> Common::Component {
            attribute :>> mass = 1.60 [kg];
            attribute :>> cost = 204.0;
            port supply : Common::PowerPort;
            part sensors : Sensor_0804[2];
            action smooth : Common::Process;
            action forward : Common::Process;
            succession first smooth then forward;
            exhibit state lifecycle : Common::Lifecycle;
        }
        requirement controllerMass_0804 : Common::MassLimit {
            subject component : Controller_0804;
            attribute :>> limit = 2.0 [kg];
        }
    }

    package Subsystem_0805 {
        part def Sensor_0805 :> Common::Component {
            attribute :>> mass = 0.20 [kg];
            attribute :>> cost = 35.0;
            attribute range : Real = 105.0;
            port data : Common::DataPort;
        }
        part def Controller_0805 :> Common::Component {
            attribute :>> mass = 1.00 [kg];
            attribute :>> cost = 205.0;
            port supply : Common::PowerPort;
            part sensors : Sensor_0805[2];
            action smooth : Common::Process;
            action forward : Common::Process;
            succession first smooth then forward;
            exhibit state lifecycle : Common::Lifecycle;
        }
        requirement controllerMass_0805 : Common::MassLimit {
            subject component : Controller_0805;
            attribute :>> limit = 2.0 [kg];
        }
    }

    package Subsystem_0806 {
        part def Sensor_0806 :> Common::Component {
            attribute :>> mass = 0.21 [kg];
            attribute :>> cost = 36.0;
            attribute range : Real = 106.0;
            port data : Common::DataPort;
        }
        part def Controller_0806 :> Common::Component {
            attribute :>> mass = 1.10 [kg];
            attribute :>> cost = 206.0;
            port supply : Common::PowerPort;
            part sensors : Sensor_0806[2];
            action smooth : Common::Process;
            action forward : Common::Process;
            succession first smooth then forward;
            exhibit state lifecycle : Common::Lifecycle;
        }
        requirement controllerMass_0806 : Common::MassLimit {
            subject component : Controller_0806;
            attribute :>> limit = 2.0 [kg];
        }
    }

    package Subsystem_0807 {
        part def Sensor_0807 :> Common::Component {
            attribute :>> mass = 0.22 [kg];
            attribute :>> cost = 37.0;
            attribute range : Real = 107.0;
            port data : Common::DataPort;
        }
        part def Controller_0807 :> Common::Component {
            attribute :>> mass = 1.20 [kg];
            attribute :>> cost = 207.0;
            port supply : Common::PowerPort;
            part sensors : Sensor_0807[2];
            action smooth : Common::Process;
            action forward : Common::Process;
            succession first smooth then forward;
            exhibit state lifecycle : Common::Lifecycle;
        }
        requirement controllerMass_0807 : Common::MassLimit {
            subject component : Controller_0807;
            attribute :>> limit = 2.0 [kg];
        }
    }

    package Subsystem_0808 {
        part def Sensor_0808 :> Common::Component {
            attribute :>> mass = 0.23 [kg];
            attribute :>> cost = 38.0;
            attribute range : Real = 108.0;
            port data : Common::DataPort;
        }
        part def Controller_0808 :> Common::Component {
            attribute :>> mass = 1.30 [kg];
            attribute :>> cost = 208.0;
            port supply : Common::PowerPort;
            part sensors : Sensor_0808[2];
            action smooth : Common::Process;
            action forward : Common::Process;
            succession first smooth then forward;
            exhibit state lifecycle : Common::Lifecycle;
        }
        requirement controllerMass_0808 : Common::MassLimit {
            subject component : Controller_0808;
            attribute :>> limit = 2.0 [kg];
        }
    }

    package Subsystem_0809 {
        part def Sensor_0809 :> Common::Component {
            attribute :>> mass = 0.24 [kg];
            attribute :>> cost = 39.0;
            attribute range : Real = 109.0;
            port data : Common::DataPort;
        }
        part def Controller_0809 :> Common::Component {
            attribute :>> mass = 1.40 [kg];
            attribute :>> cost = 209.0;
            port supply : Common::PowerPort;
            part sensors : Sensor_0809[2];
            action smooth : Common::Process;
            action forward : Common::Process;
            succession first smooth then forward;
            exhibit state lifecycle : Common::Lifecycle;
        }
        requirement controllerMass_0809 : Common::MassLimit {
            subject component : Controller_0809;
            attribute :>> limit = 2.0 [kg];
        }
    }

    package Subsystem_0810 {
        part def Sensor_0810 :> Common::Component {
            attribute :>> mass = 0.20 [kg];
            attribute :>> cost = 40.0;
            attribute range : Real = 110.0;
            port data : Common::DataPort;
        }
        part def Controller_0810 :> Common::Component {
            attribute :>> mass = 1.50 [kg];
            attribute :>> cost = 210.0;
            port supply : Common::PowerPort;
            part sensors : Sensor_0810[2];
            action smooth : Common::Process;
            action forward : Common::Process;
            succession first smooth then forward;
            exhibit state lifecycle : Common::Lifecycle;
        }
        requirement controllerMass_0810 : Common::MassLimit {
            subject component : Controller_0810;
            attribute :>> limit = 2.0 [kg];
        }
    }

    package Subsystem_0811 {
        part def Sensor_0811 :> Common::Component {
            attribute :>> mass = 0.21 [kg];
            attribute :>> cost = 41.0;
            attribute range : Real = 111.0;
            port data : Common::DataPort;
        }
        part def Controller_0811 :> Common::Component {
            attribute :>> mass = 1.60 [kg];
            attribute :>> cost = 211.0;
            port supply : Common::PowerPort;
            part sensors : Sensor_0811[2];
            action smooth : Common::Process;
            action forward : Common::Process;
            succession first smooth then forward;
            exhibit state lifecycle : Common::Lifecycle;
        }
        requirement controllerMass_0811 : Common::MassLimit {
            subject component : Controller_0811;
            attribute :>> limit = 2.0 [kg];
        }
    }

    package Subsystem_0812 {
        part def Sensor_0812 :> Common::Component {
            attribute :>> mass = 0.22 [kg];
            attribute :>> cost = 42.0;
            attribute range : Real = 112.0;
            port data : Common::DataPort;
        }
        part def Controller_0812 :> Common::Component {
            attribute :>> mass = 1.00 [kg];
            attribute :>> cost = 212.0;
            port supply : Common::PowerPort;
            part sensors : Sensor_0812[2];
            action smooth : Common::Process;
            action forward : Common::Process;
            succession first smooth then forward;
            exhibit state lifecycle : Common::Lifecycle;
        }
        requirement controllerMass_0812 : Common::MassLimit {
            subject component : Controller_0812;
            attribute :>> limit = 2.0 [kg];
        }
    }

    package Subsystem_0813 {
        part def Sensor_0813 :> Common::Component {
            attribute :>> mass = 0.23 [kg];
            attribute :>> cost = 43.0;
            attribute range : Real = 113.0;
            port data : Common::DataPort;
        }
        part def Controller_0813 :> Common::Component {
            attribute :>> mass = 1.10 [kg];
            attribute :>> cost = 213.0;
            port supply : Common::PowerPort;
            part sensors : Sensor_0813[2];
            action smooth : Common::Process;
            action forward : Common::Process;
            succession first smooth then forward;
            exhibit state lifecycle : Common::Lifecycle;
        }
        requirement controllerMass_0813 : Common::MassLimit {
            subject component : Controller_0813;
            attribute :>> limit = 2.0 [kg];
        }
    }

    package Subsystem_0814 {
        part def Sensor_0814 :> Common::Component {
            attribute :>> mass = 0.24 [kg];
            attribute :>> cost = 44.0;
            attribute range : Real = 114.0;
            port data : Common::DataPort;
        }
        part def Controller_0814 :> Common::Component {
            attribute :>> mass = 1.20 [kg];
            attribute :>> cost = 214.0;
            port supply : Common::PowerPort;
            part sensors : Sensor_0814[2];
            action smooth : Common::Process;
            action forward : Common::Process;
            succession first smooth then forward;
            exhibit state lifecycle : Common::Lifecycle;
        }
        requirement controllerMass_0814 : Common::MassLimit {
            subject component : Controller_0814;
            attribute :>> limit = 2.0 [kg];
        }
    }

    package Subsystem_0815 {
        part def Sensor_0815 :> Common::Component {
            attribute :>> mass = 0.20 [kg];
            attribute :>> cost = 45.0;
            attribute range : Real = 115.0;
            port data : Common::DataPort;
        }
        part def Controller_0815 :> Common::Component {
            attribute :>> mass = 1.30 [kg];
            attribute :>> cost = 215.0;
            port supply : Common::PowerPort;
            part sensors : Sensor_0815[2];
            action smooth : Common::Process;
            action forward : Common::Process;
            succession first smooth then forward;
            exhibit state lifecycle : Common::Lifecycle;
        }
        requirement controllerMass_0815 : Common::MassLimit {
            subject component : Controller_0815;
            attribute :>> limit = 2.0 [kg];
        }
    }

    package Subsystem_0816 {
        part def Sensor_0816 :> Common::Component {
            attribute :>> mass = 0.21 [kg];
            attribute :>> cost = 46.0;
            attribute range : Real = 116.0;
            port data : Common::DataPort;
        }
        part def Controller_0816 :> Common::Component {
            attribute :>> mass = 1.40 [kg];
            attribute :>> cost = 216.0;
            port supply : Common::PowerPort;
            part sensors : Sensor_0816[2];
            action smooth : Common::Process;
            action forward : Common::Process;
            succession first smooth then forward;
            exhibit state lifecycle : Common::Lifecycle;
        }
        requirement controllerMass_0816 : Common::MassLimit {
            subject component : Controller_0816;
            attribute :>> limit = 2.0 [kg];
        }
    }

    package Subsystem_0817 {
        part def Sensor_0817 :> Common::Component {
            attribute :>> mass = 0.22 [kg];
            attribute :>> cost = 47.0;
            attribute range : Real = 117.0;
            port data : Common::DataPort;
        }
        part def Controller_0817 :> Common::Component {
            attribute :>> mass = 1.50 [kg];
            attribute :>> cost = 217.0;
            port supply : Common::PowerPort;
            part sensors : Sensor_0817[2];
            action smooth : Common::Process;
            action forward : Common::Process;
            succession first smooth then forward;
            exhibit state lifecycle : Common::Lifecycle;
        }
        requirement controllerMass_0817 : Common::MassLimit {
            subject component : Controller_0817;
            attribute :>> limit = 2.0 [kg];
        }
    }

    package Subsystem_0818 {
        part def Sensor_0818 :> Common::Component {
            attribute :>> mass = 0.23 [kg];
            attribute :>> cost = 48.0;
            attribute range : Real = 118.0;
            port data : Common::DataPort;
        }
        part def Controller_0818 :> Common::Component {
            attribute :>> mass = 1.60 [kg];
            attribute :>> cost = 218.0;
            port supply : Common::PowerPort;
            part sensors : Sensor_0818[2];
            action smooth : Common::Process;
            action forward : Common::Process;
            succession first smooth then forward;
            exhibit state lifecycle : Common::Lifecycle;
        }
        requirement controllerMass_0818 : Common::MassLimit {
            subject component : Controller_0818;
            attribute :>> limit = 2.0 [kg];
        }
    }

    package Subsystem_0819 {
        part def Sensor_0819 :> Common::Component {
            attribute :>> mass = 0.24 [kg];
            attribute :>> cost = 49.0;
            attribute range : Real = 119.0;
            port data : Common::DataPort;
        }
        part def Controller_0819 :> Common::Component {
            attribute :>> mass = 1.00 [kg];
            attribute :>> cost = 219.0;
            port supply : Common::PowerPort;
            part sensors : Sensor_0819[2];
            action smooth : Common::Process;
            action forward : Common::Process;
            succession first smooth then forward;
            exhibit state lifecycle : Common::Lifecycle;
        }
        requirement controllerMass_0819 : Common::MassLimit {
            subject component : Controller_0819;
            attribute :>> limit = 2.0 [kg];
        }
    }

    package Subsystem_0820 {
        part def Sensor_0820 :> Common::Component {
            attribute :>> mass = 0.20 [kg];
            attribute :>> cost = 30.0;
            attribute range : Real = 120.0;
            port data : Common::DataPort;
        }
        part def Controller_0820 :> Common::Component {
            attribute :>> mass = 1.10 [kg];
            attribute :>> cost = 220.0;
            port supply : Common::PowerPort;
            part sensors : Sensor_0820[2];
            action smooth : Common::Process;
            action forward : Common::Process;
            succession first smooth then forward;
            exhibit state lifecycle : Common::Lifecycle;
        }
        requirement controllerMass_0820 : Common::MassLimit {
            subject component : Controller_0820;
            attribute :>> limit = 2.0 [kg];
        }
    }

    package Subsystem_0821 {
        part def Sensor_0821 :> Common::Component {
            attribute :>> mass = 0.21 [kg];
            attribute :>> cost = 31.0;
            attribute range : Real = 121.0;
            port data : Common::DataPort;
        }
        part def Controller_0821 :> Common::Component {
            attribute :>> mass = 1.20 [kg];
            attribute :>> cost = 221.0;
            port supply : Common::PowerPort;
            part sensors : Sensor_0821[2];
            action smooth : Common::Process;
            action forward : Common::Process;
            succession first smooth then forward;
            exhibit state lifecycle : Common::Lifecycle;
        }
        requirement controllerMass_0821 : Common::MassLimit {
            subject component : Controller_0821;
            attribute :>> limit = 2.0 [kg];
        }
    }

    package Subsystem_0822 {
        part def Sensor_0822 :> Common::Component {
            attribute :>> mass = 0.22 [kg];
            attribute :>> cost = 32.0;
            attribute range : Real = 122.0;
            port data : Common::DataPort;
        }
        part def Controller_0822 :> Common::Component {
            attribute :>> mass = 1.30 [kg];
            attribute :>> cost = 222.0;
            port supply : Common::PowerPort;
            part sensors : Sensor_0822[2];
            action smooth : Common::Process;
            action forward : Common::Process;
            succession first smooth then forward;
            exhibit state lifecycle : Common::Lifecycle;
        }
        requirement controllerMass_0822 : Common::MassLimit {
            subject component : Controller_0822;
            attribute :>> limit = 2.0 [kg];
        }
    }

    package Subsystem_0823 {
        part def Sensor_0823 :> Common::Component {
            attribute :>> mass = 0.23 [kg];
            attribute :>> cost = 33.0;
            attribute range : Real = 123.0;
            port data : Common::DataPort;
        }
        part def Controller_0823 :> Common::Component {
            attribute :>> mass = 1.40 [kg];
            attribute :>> cost = 223.0;
            port supply : Common::PowerPort;
            part sensors : Sensor_0823[2];
            action smooth : Common::Process;
            action forward : Common::Process;
            succession first smooth then forward;
            exhibit state lifecycle : Common::Lifecycle;
        }
        requirement controllerMass_0823 : Common::MassLimit {
            subject component : Controller_0823;
            attribute :>> limit = 2.0 [kg];
        }
    }

    package Subsystem_0824 {
        part def Sensor_0824 :> Common::Component {
            attribute :>> mass = 0.24 [kg];
            attribute :>> cost = 34.0;
            attribute range : Real = 124.0;
            port data : Common::DataPort;
        }
        part def Controller_0824 :> Common::Component {
            attribute :>> mass = 1.50 [kg];
            attribute :>> cost = 224.0;
            port supply : Common::PowerPort;
            part sensors : Sensor_0824[2];
            action smooth : Common::Process;
            action forward : Common::Process;
            succession first smooth then forward;
            exhibit state lifecycle : Common::Lifecycle;
        }
        requirement controllerMass_0824 : Common::MassLimit {
            subject component : Controller_0824;
            attribute :>> limit = 2.0 [kg];
        }
    }

    package Subsystem_0825 {
        part def Sensor_0825 :> Common::Component {
            attribute :>> mass = 0.20 [kg];
            attribute :>> cost = 35.0;
            attribute range : Real = 125.0;
            port data : Common::DataPort;
        }
        part def Controller_0825 :> Common::Component {
            attribute :>> mass = 1.60 [kg];
            attribute :>> cost = 225.0;
            port supply : Common::PowerPort;
            part sensors : Sensor_0825[2];
            action smooth : Common::Process;
            action forward : Common::Process;
            succession first smooth then forward;
            exhibit state lifecycle : Common::Lifecycle;
        }
        requirement controllerMass_0825 : Common::MassLimit {
            subject component : Controller_0825;
            attribute :>> limit = 2.0 [kg];
        }
    }

    package Subsystem_0826 {
        part def Sensor_0826 :> Common::Component {
            attribute :>> mass = 0.21 [kg];
            attribute :>> cost = 36.0;
            attribute range : Real = 126.0;
            port data : Common::DataPort;
        }
        part def Controller_0826 :> Common::Component {
            attribute :>> mass = 1.00 [kg];
            attribute :>> cost = 226.0;
            port supply : Common::PowerPort;
            part sensors : Sensor_0826[2];
            action smooth : Common::Process;
            action forward : Common::Process;
            succession first smooth then forward;
            exhibit state lifecycle : Common::Lifecycle;
        }
        requirement controllerMass_0826 : Common::MassLimit {
            subject component : Controller_0826;
            attribute :>> limit = 2.0 [kg];
        }
    }

    package Subsystem_0827 {
        part def Sensor_0827 :> Common::Component {
            attribute :>> mass = 0.22 [kg];
            attribute :>> cost = 37.0;
            attribute range : Real = 127.0;
            port data : Common::DataPort;
        }
        part def Controller_0827 :> Common::Component {
            attribute :>> mass = 1.10 [kg];
            attribute :>> cost = 227.0;
            port supply : Common::PowerPort;
            part sensors : Sensor_0827[2];
            action smooth : Common::Process;
            action forward : Common::Process;
            succession first smooth then forward;
            exhibit state lifecycle : Common::Lifecycle;
        }
        requirement controllerMass_0827 : Common::MassLimit {
            subject component : Controller_0827;
            attribute :>> limit = 2.0 [kg];
        }
    }

    package Subsystem_0828 {
        part def Sensor_0828 :> Common::Component {
            attribute :>> mass = 0.23 [kg];
            attribute :>> cost = 38.0;
            attribute range : Real = 128.0;
            port data : Common::DataPort;
        }
        part def Controller_0828 :> Common::Component {
            attribute :>> mass = 1.20 [kg];
            attribute :>> cost = 228.0;
            port supply : Common::PowerPort;
            part sensors : Sensor_0828[2];
            action smooth : Common::Process;
            action forward : Common::Process;
            succession first smooth then forward;
            exhibit state lifecycle : Common::Lifecycle;
        }
        requirement controllerMass_0828 : Common::MassLimit {
            subject component : Controller_0828;
            attribute :>> limit = 2.0 [kg];
        }
    }

    package Subsystem_0829 {
        part def Sensor_0829 :> Common::Component {
            attribute :>> mass = 0.24 [kg];
            attribute :>> cost = 39.0;
            attribute range : Real = 129.0;
            port data : Common::DataPort;
        }
        part def Controller_0829 :> Common::Component {
            attribute :>> mass = 1.30 [kg];
            attribute :>> cost = 229.0;
            port supply : Common::PowerPort;
            part sensors : Sensor_0829[2];
            action smooth : Common::Process;
            action forward : Common::Process;
            succession first smooth then forward;
            exhibit state lifecycle : Common::Lifecycle;
        }
        requirement controllerMass_0829 : Common::MassLimit {
            subject component : Controller_0829;
            attribute :>> limit = 2.0 [kg];
        }
    }

    package Subsystem_0830 {
        part def Sensor_0830 :> Common::Component {
            attribute :>> mass = 0.20 [kg];
            attribute :>> cost = 40.0;
            attribute range : Real = 130.0;
            port data : Common::DataPort;
        }
        part def Controller_0830 :> Common::Component {
            attribute :>> mass = 1.40 [kg];
            attribute :>> cost = 230.0;
            port supply : Common::PowerPort;
            part sensors : Sensor_0830[2];
            action smooth : Common::Process;
            action forward : Common::Process;
            succession first smooth then forward;
            exhibit state lifecycle : Common::Lifecycle;
        }
        requirement controllerMass_0830 : Common::MassLimit {
            subject component : Controller_0830;
            attribute :>> limit = 2.0 [kg];
        }
    }

    package Subsystem_0831 {
        part def Sensor_0831 :> Common::Component {
            attribute :>> mass = 0.21 [kg];
            attribute :>> cost = 41.0;
            attribute range : Real = 131.0;
            port data : Common::DataPort;
        }
        part def Controller_0831 :> Common::Component {
            attribute :>> mass = 1.50 [kg];
            attribute :>> cost = 231.0;
            port supply : Common::PowerPort;
            part sensors : Sensor_0831[2];
            action smooth : Common::Process;
            action forward : Common::Process;
            succession first smooth then forward;
            exhibit state lifecycle : Common::Lifecycle;
        }
        requirement controllerMass_0831 : Common::MassLimit {
            subject component : Controller_0831;
            attribute :>> limit = 2.0 [kg];
        }
    }

    package Subsystem_0832 {
        part def Sensor_0832 :> Common::Component {
            attribute :>> mass = 0.22 [kg];
            attribute :>> cost = 42.0;
            attribute range : Real = 132.0;
            port data : Common::DataPort;
        }
        part def Controller_0832 :> Common::Component {
            attribute :>> mass = 1.60 [kg];
            attribute :>> cost = 232.0;
            port supply : Common::PowerPort;
            part sensors : Sensor_0832[2];
            action smooth : Common::Process;
            action forward : Common::Process;
            succession first smooth then forward;
            exhibit state lifecycle : Common::Lifecycle;
        }
        requirement controllerMass_0832 : Common::MassLimit {
            subject component : Controller_0832;
            attribute :>> limit = 2.0 [kg];
        }
    }

    package Subsystem_0833 {
        part def Sensor_0833 :> Common::Component {
            attribute :>> mass = 0.23 [kg];
            attribute :>> cost = 43.0;
            attribute range : Real = 133.0;
            port data : Common::DataPort;
        }
        part def Controller_0833 :> Common::Component {
            attribute :>> mass = 1.00 [kg];
            attribute :>> cost = 233.0;
            port supply : Common::PowerPort;
            part sensors : Sensor_0833[2];
            action smooth : Common::Process;
            action forward : Common::Process;
            succession first smooth then forward;
            exhibit state lifecycle : Common::Lifecycle;
        }
        requirement controllerMass_0833 : Common::MassLimit {
            subject component : Controller_0833;
            attribute :>> limit = 2.0 [kg];
        }
    }

    package Subsystem_0834 {
        part def Sensor_0834 :> Common::Component {
            attribute :>> mass = 0.24 [kg];
            attribute :>> cost = 44.0;
            attribute range : Real = 134.0;
            port data : Common::DataPort;
        }
        part def Controller_0834 :> Common::Component {
            attribute :>> mass = 1.10 [kg];
            attribute :>> cost = 234.0;
            port supply : Common::PowerPort;
            part sensors : Sensor_0834[2];
            action smooth : Common::Process;
            action forward : Common::Process;
            succession first smooth then forward;
            exhibit state lifecycle : Common::Lifecycle;
        }
        requirement controllerMass_0834 : Common::MassLimit {
            subject component : Controller_0834;
            attribute :>> limit = 2.0 [kg];
        }
    }

    package Subsystem_0835 {
        part def Sensor_0835 :> Common::Component {
            attribute :>> mass = 0.20 [kg];
            attribute :>> cost = 45.0;
            attribute range : Real = 135.0;
            port data : Common::DataPort;
        }
        part def Controller_0835 :> Common::Component {
            attribute :>> mass = 1.20 [kg];
            attribute :>> cost = 235.0;
            port supply : Common::PowerPort;
            part sensors : Sensor_0835[2];
            action smooth : Common::Process;
            action forward : Common::Process;
            succession first smooth then forward;
            exhibit state lifecycle : Common::Lifecycle;
        }
        requirement controllerMass_0835 : Common::MassLimit {
            subject component : Controller_0835;
            attribute :>> limit = 2.0 [kg];
        }
    }

    package Subsystem_0836 {
        part def Sensor_0836 :> Common::Component {
            attribute :>> mass = 0.21 [kg];
            attribute :>> cost = 46.0;
            attribute range : Real = 136.0;
            port data : Common::DataPort;
        }
        part def Controller_0836 :> Common::Component {
            attribute :>> mass = 1.30 [kg];
            attribute :>> cost = 236.0;
            port supply : Common::PowerPort;
            part sensors : Sensor_0836[2];
            action smooth : Common::Process;
            action forward : Common::Process;
            succession first smooth then forward;
            exhibit state lifecycle : Common::Lifecycle;
        }
        requirement controllerMass_0836 : Common::MassLimit {
            subject component : Controller_0836;
            attribute :>> limit = 2.0 [kg];
        }
    }

    package Subsystem_0837 {
        part def Sensor_0837 :> Common::Component {
            attribute :>> mass = 0.22 [kg];
            attribute :>> cost = 47.0;
            attribute range : Real = 137.0;
            port data : Common::DataPort;
        }
        part def Controller_0837 :> Common::Component {
            attribute :>> mass = 1.40 [kg];
            attribute :>> cost = 237.0;
            port supply : Common::PowerPort;
            part sensors : Sensor_0837[2];
            action smooth : Common::Process;
            action forward : Common::Process;
            succession first smooth then forward;
            exhibit state lifecycle : Common::Lifecycle;
        }
        requirement controllerMass_0837 : Common::MassLimit {
            subject component : Controller_0837;
            attribute :>> limit = 2.0 [kg];
        }
    }

    package Subsystem_0838 {
        part def Sensor_0838 :> Common::Component {
            attribute :>> mass = 0.23 [kg];
            attribute :>> cost = 48.0;
            attribute range : Real = 138.0;
            port data : Common::DataPort;
        }
        part def Controller_0838 :> Common::Component {
            attribute :>> mass = 1.50 [kg];
            attribute :>> cost = 238.0;
            port supply : Common::PowerPort;
            part sensors : Sensor_0838[2];
            action smooth : Common::Process;
            action forward : Common::Process;
            succession first smooth then forward;
            exhibit state lifecycle : Common::Lifecycle;
        }
        requirement controllerMass_0838 : Common::MassLimit {
            subject component : Controller_0838;
            attribute :>> limit = 2.0 [kg];
        }
    }

    package Subsystem_0839 {
        part def Sensor_0839 :> Common::Component {
            attribute :>> mass = 0.24 [kg];
            attribute :>> cost = 49.0;
            attribute range : Real = 139.0;
            port data : Common::DataPort;
        }
        part def Controller_0839 :> Common::Component {
            attribute :>> mass = 1.60 [kg];
            attribute :>> cost = 239.0;
            port supply : Common::PowerPort;
            part sensors : Sensor_0839[2];
            action smooth : Common::Process;
            action forward : Common::Process;
            succession first smooth then forward;
            exhibit state lifecycle : Common::Lifecycle;
        }
        requirement controllerMass_0839 : Common::MassLimit {
            subject component : Controller_0839;
            attribute :>> limit = 2.0 [kg];
        }
    }

    package Subsystem_0840 {
        part def Sensor_0840 :> Common::Component {
            attribute :>> mass = 0.20 [kg];
            attribute :>> cost = 30.0;
            attribute range : Real = 140.0;
            port data : Common::DataPort;
        }
        part def Controller_0840 :> Common::Component {
            attribute :>> mass = 1.00 [kg];
            attribute :>> cost = 240.0;
            port supply : Common::PowerPort;
            part sensors : Sensor_0840[2];
            action smooth : Common::Process;
            action forward : Common::Process;
            succession first smooth then forward;
            exhibit state lifecycle : Common::Lifecycle;
        }
        requirement controllerMass_0840 : Common::MassLimit {
            subject component : Controller_0840;
            attribute :>> limit = 2.0 [kg];
        }
    }

    package Subsystem_0841 {
        part def Sensor_0841 :> Common::Component {
            attribute :>> mass = 0.21 [kg];
            attribute :>> cost = 31.0;
            attribute range : Real = 141.0;
            port data : Common::DataPort;
        }
        part def Controller_0841 :> Common::Component {
            attribute :>> mass = 1.10 [kg];
            attribute :>> cost = 241.0;
            port supply : Common::PowerPort;
            part sensors : Sensor_0841[2];
            action smooth : Common::Process;
            action forward : Common::Process;
            succession first smooth then forward;
            exhibit state lifecycle : Common::Lifecycle;
        }
        requirement controllerMass_0841 : Common::MassLimit {
            subject component : Controller_0841;
            attribute :>> limit = 2.0 [kg];
        }
    }

    package Subsystem_0842 {
        part def Sensor_0842 :> Common::Component {
            attribute :>> mass = 0.22 [kg];
            attribute :>> cost = 32.0;
            attribute range : Real = 142.0;
            port data : Common::DataPort;
        }
        part def Controller_0842 :> Common::Component {
            attribute :>> mass = 1.20 [kg];
            attribute :>> cost = 242.0;
            port supply : Common::PowerPort;
            part sensors : Sensor_0842[2];
            action smooth : Common::Process;
            action forward : Common::Process;
            succession first smooth then forward;
            exhibit state lifecycle : Common::Lifecycle;
        }
        requirement controllerMass_0842 : Common::MassLimit {
            subject component : Controller_0842;
            attribute :>> limit = 2.0 [kg];
        }
    }

    package Subsystem_0843 {
        part def Sensor_0843 :> Common::Component {
            attribute :>> mass = 0.23 [kg];
            attribute :>> cost = 33.0;
            attribute range : Real = 143.0;
            port data : Common::DataPort;
        }
        part def Controller_0843 :> Common::Component {
            attribute :>> mass = 1.30 [kg];
            attribute :>> cost = 243.0;
            port supply : Common::PowerPort;
            part sensors : Sensor_0843[2];
            action smooth : Common::Process;
            action forward : Common::Process;
            succession first smooth then forward;
            exhibit state lifecycle : Common::Lifecycle;
        }
        requirement controllerMass_0843 : Common::MassLimit {
            subject component : Controller_0843;
            attribute :>> limit = 2.0 [kg];
        }
    }

    package Subsystem_0844 {
        part def Sensor_0844 :> Common::Component {
            attribute :>> mass = 0.24 [kg];
            attribute :>> cost = 34.0;
            attribute range : Real = 144.0;
            port data : Common::DataPort;
        }
        part def Controller_0844 :> Common::Component {
            attribute :>> mass = 1.40 [kg];
            attribute :>> cost = 244.0;
            port supply : Common::PowerPort;
            part sensors : Sensor_0844[2];
            action smooth : Common::Process;
            action forward : Common::Process;
            succession first smooth then forward;
            exhibit state lifecycle : Common::Lifecycle;
        }
        requirement controllerMass_0844 : Common::MassLimit {
            subject component : Controller_0844;
            attribute :>> limit = 2.0 [kg];
        }
    }

    package Subsystem_0845 {
        part def Sensor_0845 :> Common::Component {
            attribute :>> mass = 0.20 [kg];
            attribute :>> cost = 35.0;
            attribute range : Real = 145.0;
            port data : Common::DataPort;
        }
        part def Controller_0845 :> Common::Component {
            attribute :>> mass = 1.50 [kg];
            attribute :>> cost = 245.0;
            port supply : Common::PowerPort;
            part sensors : Sensor_0845[2];
            action smooth : Common::Process;
            action forward : Common::Process;
            succession first smooth then forward;
            exhibit state lifecycle : Common::Lifecycle;
        }
        requirement controllerMass_0845 : Common::MassLimit {
            subject component : Controller_0845;
            attribute :>> limit = 2.0 [kg];
        }
    }

    package Subsystem_0846 {
        part def Sensor_0846 :> Common::Component {
            attribute :>> mass = 0.21 [kg];
            attribute :>> cost = 36.0;
            attribute range : Real = 146.0;
            port data : Common::DataPort;
        }
        part def Controller_0846 :> Common::Component {
            attribute :>> mass = 1.60 [kg];
            attribute :>> cost = 246.0;
            port supply : Common::PowerPort;
            part sensors : Sensor_0846[2];
            action smooth : Common::Process;
            action forward : Common::Process;
            succession first smooth then forward;
            exhibit state lifecycle : Common::Lifecycle;
        }
        requirement controllerMass_0846 : Common::MassLimit {
            subject component : Controller_0846;
            attribute :>> limit = 2.0 [kg];
        }
    }

    package Subsystem_0847 {
        part def Sensor_0847 :> Common::Component {
            attribute :>> mass = 0.22 [kg];
            attribute :>> cost = 37.0;
            attribute range : Real = 147.0;
            port data : Common::DataPort;
        }
        part def Controller_0847 :> Common::Component {
            attribute :>> mass = 1.00 [kg];
            attribute :>> cost = 247.0;
            port supply : Common::PowerPort;
            part sensors : Sensor_0847[2];
            action smooth : Common::Process;
            action forward : Common::Process;
            succession first smooth then forward;
            exhibit state lifecycle : Common::Lifecycle;
        }
        requirement controllerMass_0847 : Common::MassLimit {
            subject component : Controller_0847;
            attribute :>> limit = 2.0 [kg];
        }
    }

    package Subsystem_0848 {
        part def Sensor_0848 :> Common::Component {
            attribute :>> mass = 0.23 [kg];
            attribute :>> cost = 38.0;
            attribute range : Real = 148.0;
            port data : Common::DataPort;
        }
        part def Controller_0848 :> Common::Component {
            attribute :>> mass = 1.10 [kg];
            attribute :>> cost = 248.0;
            port supply : Common::PowerPort;
            part sensors : Sensor_0848[2];
            action smooth : Common::Process;
            action forward : Common::Process;
            succession first smooth then forward;
            exhibit state lifecycle : Common::Lifecycle;
        }
        requirement controllerMass_0848 : Common::MassLimit {
            subject component : Controller_0848;
            attribute :>> limit = 2.0 [kg];
        }
    }

    package Subsystem_0849 {
        part def Sensor_0849 :> Common::Component {
            attribute :>> mass = 0.24 [kg];
            attribute :>> cost = 39.0;
            attribute range : Real = 149.0;
            port data : Common::DataPort;
        }
        part def Controller_0849 :> Common::Component {
            attribute :>> mass = 1.20 [kg];
            attribute :>> cost = 249.0;
            port supply : Common::PowerPort;
            part sensors : Sensor_0849[2];
            action smooth : Common::Process;
            action forward : Common::Process;
            succession first smooth then forward;
            exhibit state lifecycle : Common::Lifecycle;
        }
        requirement controllerMass_0849 : Common::MassLimit {
            subject component : Controller_0849;
            attribute :>> limit = 2.0 [kg];
        }
    }

    package Subsystem_0850 {
        part def Sensor_0850 :> Common::Component {
            attribute :>> mass = 0.20 [kg];
            attribute :>> cost = 40.0;
            attribute range : Real = 100.0;
            port data : Common::DataPort;
        }
        part def Controller_0850 :> Common::Component {
            attribute :>> mass = 1.30 [kg];
            attribute :>> cost = 250.0;
            port supply : Common::PowerPort;
            part sensors : Sensor_0850[2];
            action smooth : Common::Process;
            action forward : Common::Process;
            succession first smooth then forward;
            exhibit state lifecycle : Common::Lifecycle;
        }
        requirement controllerMass_0850 : Common::MassLimit {
            subject component : Controller_0850;
            attribute :>> limit = 2.0 [kg];
        }
    }

    package Subsystem_0851 {
        part def Sensor_0851 :> Common::Component {
            attribute :>> mass = 0.21 [kg];
            attribute :>> cost = 41.0;
            attribute range : Real = 101.0;
            port data : Common::DataPort;
        }
        part def Controller_0851 :> Common::Component {
            attribute :>> mass = 1.40 [kg];
            attribute :>> cost = 251.0;
            port supply : Common::PowerPort;
            part sensors : Sensor_0851[2];
            action smooth : Common::Process;
            action forward : Common::Process;
            succession first smooth then forward;
            exhibit state lifecycle : Common::Lifecycle;
        }
        requirement controllerMass_0851 : Common::MassLimit {
            subject component : Controller_0851;
            attribute :>> limit = 2.0 [kg];
        }
    }

    package Subsystem_0852 {
        part def Sensor_0852 :> Common::Component {
            attribute :>> mass = 0.22 [kg];
            attribute :>> cost = 42.0;
            attribute range : Real = 102.0;
            port data : Common::DataPort;
        }
        part def Controller_0852 :> Common::Component {
            attribute :>> mass = 1.50 [kg];
            attribute :>> cost = 252.0;
            port supply : Common::PowerPort;
            part sensors : Sensor_0852[2];
            action smooth : Common::Process;
            action forward : Common::Process;
            succession first smooth then forward;
            exhibit state lifecycle : Common::Lifecycle;
        }
        requirement controllerMass_0852 : Common::MassLimit {
            subject component : Controller_0852;
            attribute :>> limit = 2.0 [kg];
        }
    }

    package Subsystem_0853 {
        part def Sensor_0853 :> Common::Component {
            attribute :>> mass = 0.23 [kg];
            attribute :>> cost = 43.0;
            attribute range : Real = 103.0;
            port data : Common::DataPort;
        }
        part def Controller_0853 :> Common::Component {
            attribute :>> mass = 1.60 [kg];
            attribute :>> cost = 253.0;
            port supply : Common::PowerPort;
            part sensors : Sensor_0853[2];
            action smooth : Common::Process;
            action forward : Common::Process;
            succession first smooth then forward;
            exhibit state lifecycle : Common::Lifecycle;
        }
        requirement controllerMass_0853 : Common::MassLimit {
            subject component : Controller_0853;
            attribute :>> limit = 2.0 [kg];
        }
    }

    package Subsystem_0854 {
        part def Sensor_0854 :> Common::Component {
            attribute :>> mass = 0.24 [kg];
            attribute :>> cost = 44.0;
            attribute range : Real = 104.0;
            port data : Common::DataPort;
        }
        part def Controller_0854 :> Common::Component {
            attribute :>> mass = 1.00 [kg];
            attribute :>> cost = 254.0;
            port supply : Common::PowerPort;
            part sensors : Sensor_0854[2];
            action smooth : Common::Process;
            action forward : Common::Process;
            succession first smooth then forward;
            exhibit state lifecycle : Common::Lifecycle;
        }
        requirement controllerMass_0854 : Common::MassLimit {
            subject component : Controller_0854;
            attribute :>> limit = 2.0 [kg];
        }
    }

    package Subsystem_0855 {
        part def Sensor_0855 :> Common::Component {
            attribute :>> mass = 0.20 [kg];
            attribute :>> cost = 45.0;
            attribute range : Real = 105.0;
            port data : Common::DataPort;
        }
        part def Controller_0855 :> Common::Component {
            attribute :>> mass = 1.10 [kg];
            attribute :>> cost = 255.0;
            port supply : Common::PowerPort;
            part sensors : Sensor_0855[2];
            action smooth : Common::Process;
            action forward : Common::Process;
            succession first smooth then forward;
            exhibit state lifecycle : Common::Lifecycle;
        }
        requirement controllerMass_0855 : Common::MassLimit {
            subject component : Controller_0855;
            attribute :>> limit = 2.0 [kg];
        }
    }

    package Subsystem_0856 {
        part def Sensor_0856 :> Common::Component {
            attribute :>> mass = 0.21 [kg];
            attribute :>> cost = 46.0;
            attribute range : Real = 106.0;
            port data : Common::DataPort;
        }
        part def Controller_0856 :> Common::Component {
            attribute :>> mass = 1.20 [kg];
            attribute :>> cost = 256.0;
            port supply : Common::PowerPort;
            part sensors : Sensor_0856[2];
            action smooth : Common::Process;
            action forward : Common::Process;
            succession first smooth then forward;
            exhibit state lifecycle : Common::Lifecycle;
        }
        requirement controllerMass_0856 : Common::MassLimit {
            subject component : Controller_0856;
            attribute :>> limit = 2.0 [kg];
        }
    }

    package Subsystem_0857 {
        part def Sensor_0857 :> Common::Component {
            attribute :>> mass = 0.22 [kg];
            attribute :>> cost = 47.0;
            attribute range : Real = 107.0;
            port data : Common::DataPort;
        }
        part def Controller_0857 :> Common::Component {
            attribute :>> mass = 1.30 [kg];
            attribute :>> cost = 257.0;
            port supply : Common::PowerPort;
            part sensors : Sensor_0857[2];
            action smooth : Common::Process;
            action forward : Common::Process;
            succession first smooth then forward;
            exhibit state lifecycle : Common::Lifecycle;
        }
        requirement controllerMass_0857 : Common::MassLimit {
            subject component : Controller_0857;
            attribute :>> limit = 2.0 [kg];
        }
    }

    package Subsystem_0858 {
        part def Sensor_0858 :> Common::Component {
            attribute :>> mass = 0.23 [kg];
            attribute :>> cost = 48.0;
            attribute range : Real = 108.0;
            port data : Common::DataPort;
        }
        part def Controller_0858 :> Common::Component {
            attribute :>> mass = 1.40 [kg];
            attribute :>> cost = 258.0;
            port supply : Common::PowerPort;
            part sensors : Sensor_0858[2];
            action smooth : Common::Process;
            action forward : Common::Process;
            succession first smooth then forward;
            exhibit state lifecycle : Common::Lifecycle;
        }
        requirement controllerMass_0858 : Common::MassLimit {
            subject component : Controller_0858;
            attribute :>> limit = 2.0 [kg];
        }
    }

    package Subsystem_0859 {
        part def Sensor_0859 :> Common::Component {
            attribute :>> mass = 0.24 [kg];
            attribute :>> cost = 49.0;
            attribute range : Real = 109.0;
            port data : Common::DataPort;
        }
        part def Controller_0859 :> Common::Component {
            attribute :>> mass = 1.50 [kg];
            attribute :>> cost = 259.0;
            port supply : Common::PowerPort;
            part sensors : Sensor_0859[2];
            action smooth : Common::Process;
            action forward : Common::Process;
            succession first smooth then forward;
            exhibit state lifecycle : Common::Lifecycle;
        }
        requirement controllerMass_0859 : Common::MassLimit {
            subject component : Controller_0859;
            attribute :>> limit = 2.0 [kg];
        }
    }

    package Subsystem_0860 {
        part def Sensor_0860 :> Common::Component {
            attribute :>> mass = 0.20 [kg];
            attribute :>> cost = 30.0;
            attribute range : Real = 110.0;
            port data : Common::DataPort;
        }
        part def Controller_0860 :> Common::Component {
            attribute :>> mass = 1.60 [kg];
            attribute :>> cost = 260.0;
            port supply : Common::PowerPort;
            part sensors : Sensor_0860[2];
            action smooth : Common::Process;
            action forward : Common::Process;
            succession first smooth then forward;
            exhibit state lifecycle : Common::Lifecycle;
        }
        requirement controllerMass_0860 : Common::MassLimit {
            subject component : Controller_0860;
            attribute :>> limit = 2.0 [kg];
        }
    }

    package Subsystem_0861 {
        part def Sensor_0861 :> Common::Component {
            attribute :>> mass = 0.21 [kg];
            attribute :>> cost = 31.0;
            attribute range : Real = 111.0;
            port data : Common::DataPort;
        }
        part def Controller_0861 :> Common::Component {
            attribute :>> mass = 1.00 [kg];
            attribute :>> cost = 261.0;
            port supply : Common::PowerPort;
            part sensors : Sensor_0861[2];
            action smooth : Common::Process;
            action forward : Common::Process;
            succession first smooth then forward;
            exhibit state lifecycle : Common::Lifecycle;
        }
        requirement controllerMass_0861 : Common::MassLimit {
            subject component : Controller_0861;
            attribute :>> limit = 2.0 [kg];
        }
    }

    package Subsystem_0862 {
        part def Sensor_0862 :> Common::Component {
            attribute :>> mass = 0.22 [kg];
            attribute :>> cost = 32.0;
            attribute range : Real = 112.0;
            port data : Common::DataPort;
        }
        part def Controller_0862 :> Common::Component {
            attribute :>> mass = 1.10 [kg];
            attribute :>> cost = 262.0;
            port supply : Common::PowerPort;
            part sensors : Sensor_0862[2];
            action smooth : Common::Process;
            action forward : Common::Process;
            succession first smooth then forward;
            exhibit state lifecycle : Common::Lifecycle;
        }
        requirement controllerMass_0862 : Common::MassLimit {
            subject component : Controller_0862;
            attribute :>> limit = 2.0 [kg];
        }
    }

    package Subsystem_0863 {
        part def Sensor_0863 :> Common::Component {
            attribute :>> mass = 0.23 [kg];
            attribute :>> cost = 33.0;
            attribute range : Real = 113.0;
            port data : Common::DataPort;
        }
        part def Controller_0863 :> Common::Component {
            attribute :>> mass = 1.20 [kg];
            attribute :>> cost = 263.0;
            port supply : Common::PowerPort;
            part sensors : Sensor_0863[2];
            action smooth : Common::Process;
            action forward : Common::Process;
            succession first smooth then forward;
            exhibit state lifecycle : Common::Lifecycle;
        }
        requirement controllerMass_0863 : Common::MassLimit {
            subject component : Controller_0863;
            attribute :>> limit = 2.0 [kg];
        }
    }

    package Subsystem_0864 {
        part def Sensor_0864 :> Common::Component {
            attribute :>> mass = 0.24 [kg];
            attribute :>> cost = 34.0;
            attribute range : Real = 114.0;
            port data : Common::DataPort;
        }
        part def Controller_0864 :> Common::Component {
            attribute :>> mass = 1.30 [kg];
            attribute :>> cost = 264.0;
            port supply : Common::PowerPort;
            part sensors : Sensor_0864[2];
            action smooth : Common::Process;
            action forward : Common::Process;
            succession first smooth then forward;
            exhibit state lifecycle : Common::Lifecycle;
        }
        requirement controllerMass_0864 : Common::MassLimit {
            subject component : Controller_0864;
            attribute :>> limit = 2.0 [kg];
        }
    }

    package Subsystem_0865 {
        part def Sensor_0865 :> Common::Component {
            attribute :>> mass = 0.20 [kg];
            attribute :>> cost = 35.0;
            attribute range : Real = 115.0;
            port data : Common::DataPort;
        }
        part def Controller_0865 :> Common::Component {
            attribute :>> mass = 1.40 [kg];
            attribute :>> cost = 265.0;
            port supply : Common::PowerPort;
            part sensors : Sensor_0865[2];
            action smooth : Common::Process;
            action forward : Common::Process;
            succession first smooth then forward;
            exhibit state lifecycle : Common::Lifecycle;
        }
        requirement controllerMass_0865 : Common::MassLimit {
            subject component : Controller_0865;
            attribute :>> limit = 2.0 [kg];
        }
    }

    package Subsystem_0866 {
        part def Sensor_0866 :> Common::Component {
            attribute :>> mass = 0.21 [kg];
            attribute :>> cost = 36.0;
            attribute range : Real = 116.0;
            port data : Common::DataPort;
        }
        part def Controller_0866 :> Common::Component {
            attribute :>> mass = 1.50 [kg];
            attribute :>> cost = 266.0;
            port supply : Common::PowerPort;
            part sensors : Sensor_0866[2];
            action smooth : Common::Process;
            action forward : Common::Process;
            succession first smooth then forward;
            exhibit state lifecycle : Common::Lifecycle;
        }
        requirement controllerMass_0866 : Common::MassLimit {
            subject component : Controller_0866;
            attribute :>> limit = 2.0 [kg];
        }
    }

    package Subsystem_0867 {
        part def Sensor_0867 :> Common::Component {
            attribute :>> mass = 0.22 [kg];
            attribute :>> cost = 37.0;
            attribute range : Real = 117.0;
            port data : Common::DataPort;
        }
        part def Controller_0867 :> Common::Component {
            attribute :>> mass = 1.60 [kg];
            attribute :>> cost = 267.0;
            port supply : Common::PowerPort;
            part sensors : Sensor_0867[2];
            action smooth : Common::Process;
            action forward : Common::Process;
            succession first smooth then forward;
            exhibit state lifecycle : Common::Lifecycle;
        }
        requirement controllerMass_0867 : Common::MassLimit {
            subject component : Controller_0867;
            attribute :>> limit = 2.0 [kg];
        }
    }

    package Subsystem_0868 {
        part def Sensor_0868 :> Common::Component {
            attribute :>> mass = 0.23 [kg];
            attribute :>> cost = 38.0;
            attribute range : Real = 118.0;
            port data : Common::DataPort;
        }
        part def Controller_0868 :> Common::Component {
            attribute :>> mass = 1.00 [kg];
            attribute :>> cost = 268.0;
            port supply : Common::PowerPort;
            part sensors : Sensor_0868[2];
            action smooth : Common::Process;
            action forward : Common::Process;
            succession first smooth then forward;
            exhibit state lifecycle : Common::Lifecycle;
        }
        requirement controllerMass_0868 : Common::MassLimit {
            subject component : Controller_0868;
            attribute :>> limit = 2.0 [kg];
        }
    }

    package Subsystem_0869 {
        part def Sensor_0869 :> Common::Component {
            attribute :>> mass = 0.24 [kg];
            attribute :>> cost = 39.0;
            attribute range : Real = 119.0;
            port data : Common::DataPort;
        }
        part def Controller_0869 :> Common::Component {
            attribute :>> mass = 1.10 [kg];
            attribute :>> cost = 269.0;
            port supply : Common::PowerPort;
            part sensors : Sensor_0869[2];
            action smooth : Common::Process;
            action forward : Common::Process;
            succession first smooth then forward;
            exhibit state lifecycle : Common::Lifecycle;
        }
        requirement controllerMass_0869 : Common::MassLimit {
            subject component : Controller_0869;
            attribute :>> limit = 2.0 [kg];
        }
    }

    package Subsystem_0870 {
        part def Sensor_0870 :> Common::Component {
            attribute :>> mass = 0.20 [kg];
            attribute :>> cost = 40.0;
            attribute range : Real = 120.0;
            port data : Common::DataPort;
        }
        part def Controller_0870 :> Common::Component {
            attribute :>> mass = 1.20 [kg];
            attribute :>> cost = 270.0;
            port supply : Common::PowerPort;
            part sensors : Sensor_0870[2];
            action smooth : Common::Process;
            action forward : Common::Process;
            succession first smooth then forward;
            exhibit state lifecycle : Common::Lifecycle;
        }
        requirement controllerMass_0870 : Common::MassLimit {
            subject component : Controller_0870;
            attribute :>> limit = 2.0 [kg];
        }
    }

    package Subsystem_0871 {
        part def Sensor_0871 :> Common::Component {
            attribute :>> mass = 0.21 [kg];
            attribute :>> cost = 41.0;
            attribute range : Real = 121.0;
            port data : Common::DataPort;
        }
        part def Controller_0871 :> Common::Component {
            attribute :>> mass = 1.30 [kg];
            attribute :>> cost = 271.0;
            port supply : Common::PowerPort;
            part sensors : Sensor_0871[2];
            action smooth : Common::Process;
            action forward : Common::Process;
            succession first smooth then forward;
            exhibit state lifecycle : Common::Lifecycle;
        }
        requirement controllerMass_0871 : Common::MassLimit {
            subject component : Controller_0871;
            attribute :>> limit = 2.0 [kg];
        }
    }

    package Subsystem_0872 {
        part def Sensor_0872 :> Common::Component {
            attribute :>> mass = 0.22 [kg];
            attribute :>> cost = 42.0;
            attribute range : Real = 122.0;
            port data : Common::DataPort;
        }
        part def Controller_0872 :> Common::Component {
            attribute :>> mass = 1.40 [kg];
            attribute :>> cost = 272.0;
            port supply : Common::PowerPort;
            part sensors : Sensor_0872[2];
            action smooth : Common::Process;
            action forward : Common::Process;
            succession first smooth then forward;
            exhibit state lifecycle : Common::Lifecycle;
        }
        requirement controllerMass_0872 : Common::MassLimit {
            subject component : Controller_0872;
            attribute :>> limit = 2.0 [kg];
        }
    }

    package Subsystem_0873 {
        part def Sensor_0873 :> Common::Component {
            attribute :>> mass = 0.23 [kg];
            attribute :>> cost = 43.0;
            attribute range : Real = 123.0;
            port data : Common::DataPort;
        }
        part def Controller_0873 :> Common::Component {
            attribute :>> mass = 1.50 [kg];
            attribute :>> cost = 273.0;
            port supply : Common::PowerPort;
            part sensors : Sensor_0873[2];
            action smooth : Common::Process;
            action forward : Common::Process;
            succession first smooth then forward;
            exhibit state lifecycle : Common::Lifecycle;
        }
        requirement controllerMass_0873 : Common::MassLimit {
            subject component : Controller_0873;
            attribute :>> limit = 2.0 [kg];
        }
    }

    package Subsystem_0874 {
        part def Sensor_0874 :> Common::Component {
            attribute :>> mass = 0.24 [kg];
            attribute :>> cost = 44.0;
            attribute range : Real = 124.0;
            port data : Common::DataPort;
        }
        part def Controller_0874 :> Common::Component {
            attribute :>> mass = 1.60 [kg];
            attribute :>> cost = 274.0;
            port supply : Common::PowerPort;
            part sensors : Sensor_0874[2];
            action smooth : Common::Process;
            action forward : Common::Process;
            succession first smooth then forward;
            exhibit state lifecycle : Common::Lifecycle;
        }
        requirement controllerMass_0874 : Common::MassLimit {
            subject component : Controller_0874;
            attribute :>> limit = 2.0 [kg];
        }
    }

    package Subsystem_0875 {
        part def Sensor_0875 :> Common::Component {
            attribute :>> mass = 0.20 [kg];
            attribute :>> cost = 45.0;
            attribute range : Real = 125.0;
            port data : Common::DataPort;
        }
        part def Controller_0875 :> Common::Component {
            attribute :>> mass = 1.00 [kg];
            attribute :>> cost = 275.0;
            port supply : Common::PowerPort;
            part sensors : Sensor_0875[2];
            action smooth : Common::Process;
            action forward : Common::Process;
            succession first smooth then forward;
            exhibit state lifecycle : Common::Lifecycle;
        }
        requirement controllerMass_0875 : Common::MassLimit {
            subject component : Controller_0875;
            attribute :>> limit = 2.0 [kg];
        }
    }

    package Subsystem_0876 {
        part def Sensor_0876 :> Common::Component {
            attribute :>> mass = 0.21 [kg];
            attribute :>> cost = 46.0;
            attribute range : Real = 126.0;
            port data : Common::DataPort;
        }
        part def Controller_0876 :> Common::Component {
            attribute :>> mass = 1.10 [kg];
            attribute :>> cost = 276.0;
            port supply : Common::PowerPort;
            part sensors : Sensor_0876[2];
            action smooth : Common::Process;
            action forward : Common::Process;
            succession first smooth then forward;
            exhibit state lifecycle : Common::Lifecycle;
        }
        requirement controllerMass_0876 : Common::MassLimit {
            subject component : Controller_0876;
            attribute :>> limit = 2.0 [kg];
        }
    }

    package Subsystem_0877 {
        part def Sensor_0877 :> Common::Component {
            attribute :>> mass = 0.22 [kg];
            attribute :>> cost = 47.0;
            attribute range : Real = 127.0;
            port data : Common::DataPort;
        }
        part def Controller_0877 :> Common::Component {
            attribute :>> mass = 1.20 [kg];
            attribute :>> cost = 277.0;
            port supply : Common::PowerPort;
            part sensors : Sensor_0877[2];
            action smooth : Common::Process;
            action forward : Common::Process;
            succession first smooth then forward;
            exhibit state lifecycle : Common::Lifecycle;
        }
        requirement controllerMass_0877 : Common::MassLimit {
            subject component : Controller_0877;
            attribute :>> limit = 2.0 [kg];
        }
    }

    package Subsystem_0878 {
        part def Sensor_0878 :> Common::Component {
            attribute :>> mass = 0.23 [kg];
            attribute :>> cost = 48.0;
            attribute range : Real = 128.0;
            port data : Common::DataPort;
        }
        part def Controller_0878 :> Common::Component {
            attribute :>> mass = 1.30 [kg];
            attribute :>> cost = 278.0;
            port supply : Common::PowerPort;
            part sensors : Sensor_0878[2];
            action smooth : Common::Process;
            action forward : Common::Process;
            succession first smooth then forward;
            exhibit state lifecycle : Common::Lifecycle;
        }
        requirement controllerMass_0878 : Common::MassLimit {
            subject component : Controller_0878;
            attribute :>> limit = 2.0 [kg];
        }
    }

    package Subsystem_0879 {
        part def Sensor_0879 :> Common::Component {
            attribute :>> mass = 0.24 [kg];
            attribute :>> cost = 49.0;
            attribute range : Real = 129.0;
            port data : Common::DataPort;
        }
        part def Controller_0879 :> Common::Component {
            attribute :>> mass = 1.40 [kg];
            attribute :>> cost = 279.0;
            port supply : Common::PowerPort;
            part sensors : Sensor_0879[2];
            action smooth : Common::Process;
            action forward : Common::Process;
            succession first smooth then forward;
            exhibit state lifecycle : Common::Lifecycle;
        }
        requirement controllerMass_0879 : Common::MassLimit {
            subject component : Controller_0879;
            attribute :>> limit = 2.0 [kg];
        }
    }

    package Subsystem_0880 {
        part def Sensor_0880 :> Common::Component {
            attribute :>> mass = 0.20 [kg];
            attribute :>> cost = 30.0;
            attribute range : Real = 130.0;
            port data : Common::DataPort;
        }
        part def Controller_0880 :> Common::Component {
            attribute :>> mass = 1.50 [kg];
            attribute :>> cost = 280.0;
            port supply : Common::PowerPort;
            part sensors : Sensor_0880[2];
            action smooth : Common::Process;
            action forward : Common::Process;
            succession first smooth then forward;
            exhibit state lifecycle : Common::Lifecycle;
        }
        requirement controllerMass_0880 : Common::MassLimit {
            subject component : Controller_0880;
            attribute :>> limit = 2.0 [kg];
        }
    }

    package Subsystem_0881 {
        part def Sensor_0881 :> Common::Component {
            attribute :>> mass = 0.21 [kg];
            attribute :>> cost = 31.0;
            attribute range : Real = 131.0;
            port data : Common::DataPort;
        }
        part def Controller_0881 :> Common::Component {
            attribute :>> mass = 1.60 [kg];
            attribute :>> cost = 281.0;
            port supply : Common::PowerPort;
            part sensors : Sensor_0881[2];
            action smooth : Common::Process;
            action forward : Common::Process;
            succession first smooth then forward;
            exhibit state lifecycle : Common::Lifecycle;
        }
        requirement controllerMass_0881 : Common::MassLimit {
            subject component : Controller_0881;
            attribute :>> limit = 2.0 [kg];
        }
    }

    package Subsystem_0882 {
        part def Sensor_0882 :> Common::Component {
            attribute :>> mass = 0.22 [kg];
            attribute :>> cost = 32.0;
            attribute range : Real = 132.0;
            port data : Common::DataPort;
        }
        part def Controller_0882 :> Common::Component {
            attribute :>> mass = 1.00 [kg];
            attribute :>> cost = 282.0;
            port supply : Common::PowerPort;
            part sensors : Sensor_0882[2];
            action smooth : Common::Process;
            action forward : Common::Process;
            succession first smooth then forward;
            exhibit state lifecycle : Common::Lifecycle;
        }
        requirement controllerMass_0882 : Common::MassLimit {
            subject component : Controller_0882;
            attribute :>> limit = 2.0 [kg];
        }
    }

    package Subsystem_0883 {
        part def Sensor_0883 :> Common::Component {
            attribute :>> mass = 0.23 [kg];
            attribute :>> cost = 33.0;
            attribute range : Real = 133.0;
            port data : Common::DataPort;
        }
        part def Controller_0883 :> Common::Component {
            attribute :>> mass = 1.10 [kg];
            attribute :>> cost = 283.0;
            port supply : Common::PowerPort;
            part sensors : Sensor_0883[2];
            action smooth : Common::Process;
            action forward : Common::Process;
            succession first smooth then forward;
            exhibit state lifecycle : Common::Lifecycle;
        }
        requirement controllerMass_0883 : Common::MassLimit {
            subject component : Controller_0883;
            attribute :>> limit = 2.0 [kg];
        }
    }

    package Subsystem_0884 {
        part def Sensor_0884 :> Common::Component {
            attribute :>> mass = 0.24 [kg];
            attribute :>> cost = 34.0;
            attribute range : Real = 134.0;
            port data : Common::DataPort;
        }
        part def Controller_0884 :> Common::Component {
            attribute :>> mass = 1.20 [kg];
            attribute :>> cost = 284.0;
            port supply : Common::PowerPort;
            part sensors : Sensor_0884[2];
            action smooth : Common::Process;
            action forward : Common::Process;
            succession first smooth then forward;
            exhibit state lifecycle : Common::Lifecycle;
        }
        requirement controllerMass_0884 : Common::MassLimit {
            subject component : Controller_0884;
            attribute :>> limit = 2.0 [kg];
        }
    }

    package Subsystem_0885 {
        part def Sensor_0885 :> Common::Component {
            attribute :>> mass = 0.20 [kg];
            attribute :>> cost = 35.0;
            attribute range : Real = 135.0;
            port data : Common::DataPort;
        }
        part def Controller_0885 :> Common::Component {
            attribute :>> mass = 1.30 [kg];
            attribute :>> cost = 285.0;
            port supply : Common::PowerPort;
            part sensors : Sensor_0885[2];
            action smooth : Common::Process;
            action forward : Common::Process;
            succession first smooth then forward;
            exhibit state lifecycle : Common::Lifecycle;
        }
        requirement controllerMass_0885 : Common::MassLimit {
            subject component : Controller_0885;
            attribute :>> limit = 2.0 [kg];
        }
    }

    package Subsystem_0886 {
        part def Sensor_0886 :> Common::Component {
            attribute :>> mass = 0.21 [kg];
            attribute :>> cost = 36.0;
            attribute range : Real = 136.0;
            port data : Common::DataPort;
        }
        part def Controller_0886 :> Common::Component {
            attribute :>> mass = 1.40 [kg];
            attribute :>> cost = 286.0;
            port supply : Common::PowerPort;
            part sensors : Sensor_0886[2];
            action smooth : Common::Process;
            action forward : Common::Process;
            succession first smooth then forward;
            exhibit state lifecycle : Common::Lifecycle;
        }
        requirement controllerMass_0886 : Common::MassLimit {
            subject component : Controller_0886;
            attribute :>> limit = 2.0 [kg];
        }
    }

    package Subsystem_0887 {
        part def Sensor_0887 :> Common::Component {
            attribute :>> mass = 0.22 [kg];
            attribute :>> cost = 37.0;
            attribute range : Real = 137.0;
            port data : Common::DataPort;
        }
        part def Controller_0887 :> Common::Component {
            attribute :>> mass = 1.50 [kg];
            attribute :>> cost = 287.0;
            port supply : Common::PowerPort;
            part sensors : Sensor_0887[2];
            action smooth : Common::Process;
            action forward : Common::Process;
            succession first smooth then forward;
            exhibit state lifecycle : Common::Lifecycle;
        }
        requirement controllerMass_0887 : Common::MassLimit {
            subject component : Controller_0887;
            attribute :>> limit = 2.0 [kg];
        }
    }

    package Subsystem_0888 {
        part def Sensor_0888 :> Common::Component {
            attribute :>> mass = 0.23 [kg];
            attribute :>> cost = 38.0;
            attribute range : Real = 138.0;
            port data : Common::DataPort;
        }
        part def Controller_0888 :> Common::Component {
            attribute :>> mass = 1.60 [kg];
            attribute :>> cost = 288.0;
            port supply : Common::PowerPort;
            part sensors : Sensor_0888[2];
            action smooth : Common::Process;
            action forward : Common::Process;
            succession first smooth then forward;
            exhibit state lifecycle : Common::Lifecycle;
        }
        requirement controllerMass_0888 : Common::MassLimit {
            subject component : Controller_0888;
            attribute :>> limit = 2.0 [kg];
        }
    }

    package Subsystem_0889 {
        part def Sensor_0889 :> Common::Component {
            attribute :>> mass = 0.24 [kg];
            attribute :>> cost = 39.0;
            attribute range : Real = 139.0;
            port data : Common::DataPort;
        }
        part def Controller_0889 :> Common::Component {
            attribute :>> mass = 1.00 [kg];
            attribute :>> cost = 289.0;
            port supply : Common::PowerPort;
            part sensors : Sensor_0889[2];
            action smooth : Common::Process;
            action forward : Common::Process;
            succession first smooth then forward;
            exhibit state lifecycle : Common::Lifecycle;
        }
        requirement controllerMass_0889 : Common::MassLimit {
            subject component : Controller_0889;
            attribute :>> limit = 2.0 [kg];
        }
    }

    package Subsystem_0890 {
        part def Sensor_0890 :> Common::Component {
            attribute :>> mass = 0.20 [kg];
            attribute :>> cost = 40.0;
            attribute range : Real = 140.0;
            port data : Common::DataPort;
        }
        part def Controller_0890 :> Common::Component {
            attribute :>> mass = 1.10 [kg];
            attribute :>> cost = 290.0;
            port supply : Common::PowerPort;
            part sensors : Sensor_0890[2];
            action smooth : Common::Process;
            action forward : Common::Process;
            succession first smooth then forward;
            exhibit state lifecycle : Common::Lifecycle;
        }
        requirement controllerMass_0890 : Common::MassLimit {
            subject component : Controller_0890;
            attribute :>> limit = 2.0 [kg];
        }
    }

    package Subsystem_0891 {
        part def Sensor_0891 :> Common::Component {
            attribute :>> mass = 0.21 [kg];
            attribute :>> cost = 41.0;
            attribute range : Real = 141.0;
            port data : Common::DataPort;
        }
        part def Controller_0891 :> Common::Component {
            attribute :>> mass = 1.20 [kg];
            attribute :>> cost = 291.0;
            port supply : Common::PowerPort;
            part sensors : Sensor_0891[2];
            action smooth : Common::Process;
            action forward : Common::Process;
            succession first smooth then forward;
            exhibit state lifecycle : Common::Lifecycle;
        }
        requirement controllerMass_0891 : Common::MassLimit {
            subject component : Controller_0891;
            attribute :>> limit = 2.0 [kg];
        }
    }

    package Subsystem_0892 {
        part def Sensor_0892 :> Common::Component {
            attribute :>> mass = 0.22 [kg];
            attribute :>> cost = 42.0;
            attribute range : Real = 142.0;
            port data : Common::DataPort;
        }
        part def Controller_0892 :> Common::Component {
            attribute :>> mass = 1.30 [kg];
            attribute :>> cost = 292.0;
            port supply : Common::PowerPort;
            part sensors : Sensor_0892[2];
            action smooth : Common::Process;
            action forward : Common::Process;
            succession first smooth then forward;
            exhibit state lifecycle : Common::Lifecycle;
        }
        requirement controllerMass_0892 : Common::MassLimit {
            subject component : Controller_0892;
            attribute :>> limit = 2.0 [kg];
        }
    }

    package Subsystem_0893 {
        part def Sensor_0893 :> Common::Component {
            attribute :>> mass = 0.23 [kg];
            attribute :>> cost = 43.0;
            attribute range : Real = 143.0;
            port data : Common::DataPort;
        }
        part def Controller_0893 :> Common::Component {
            attribute :>> mass = 1.40 [kg];
            attribute :>> cost = 293.0;
            port supply : Common::PowerPort;
            part sensors : Sensor_0893[2];
            action smooth : Common::Process;
            action forward : Common::Process;
            succession first smooth then forward;
            exhibit state lifecycle : Common::Lifecycle;
        }
        requirement controllerMass_0893 : Common::MassLimit {
            subject component : Controller_0893;
            attribute :>> limit = 2.0 [kg];
        }
    }

    package Subsystem_0894 {
        part def Sensor_0894 :> Common::Component {
            attribute :>> mass = 0.24 [kg];
            attribute :>> cost = 44.0;
            attribute range : Real = 144.0;
            port data : Common::DataPort;
        }
        part def Controller_0894 :> Common::Component {
            attribute :>> mass = 1.50 [kg];
            attribute :>> cost = 294.0;
            port supply : Common::PowerPort;
            part sensors : Sensor_0894[2];
            action smooth : Common::Process;
            action forward : Common::Process;
            succession first smooth then forward;
            exhibit state lifecycle : Common::Lifecycle;
        }
        requirement controllerMass_0894 : Common::MassLimit {
            subject component : Controller_0894;
            attribute :>> limit = 2.0 [kg];
        }
    }

    package Subsystem_0895 {
        part def Sensor_0895 :> Common::Component {
            attribute :>> mass = 0.20 [kg];
            attribute :>> cost = 45.0;
            attribute range : Real = 145.0;
            port data : Common::DataPort;
        }
        part def Controller_0895 :> Common::Component {
            attribute :>> mass = 1.60 [kg];
            attribute :>> cost = 295.0;
            port supply : Common::PowerPort;
            part sensors : Sensor_0895[2];
            action smooth : Common::Process;
            action forward : Common::Process;
            succession first smooth then forward;
            exhibit state lifecycle : Common::Lifecycle;
        }
        requirement controllerMass_0895 : Common::MassLimit {
            subject component : Controller_0895;
            attribute :>> limit = 2.0 [kg];
        }
    }

    package Subsystem_0896 {
        part def Sensor_0896 :> Common::Component {
            attribute :>> mass = 0.21 [kg];
            attribute :>> cost = 46.0;
            attribute range : Real = 146.0;
            port data : Common::DataPort;
        }
        part def Controller_0896 :> Common::Component {
            attribute :>> mass = 1.00 [kg];
            attribute :>> cost = 296.0;
            port supply : Common::PowerPort;
            part sensors : Sensor_0896[2];
            action smooth : Common::Process;
            action forward : Common::Process;
            succession first smooth then forward;
            exhibit state lifecycle : Common::Lifecycle;
        }
        requirement controllerMass_0896 : Common::MassLimit {
            subject component : Controller_0896;
            attribute :>> limit = 2.0 [kg];
        }
    }

    package Subsystem_0897 {
        part def Sensor_0897 :> Common::Component {
            attribute :>> mass = 0.22 [kg];
            attribute :>> cost = 47.0;
            attribute range : Real = 147.0;
            port data : Common::DataPort;
        }
        part def Controller_0897 :> Common::Component {
            attribute :>> mass = 1.10 [kg];
            attribute :>> cost = 297.0;
            port supply : Common::PowerPort;
            part sensors : Sensor_0897[2];
            action smooth : Common::Process;
            action forward : Common::Process;
            succession first smooth then forward;
            exhibit state lifecycle : Common::Lifecycle;
        }
        requirement controllerMass_0897 : Common::MassLimit {
            subject component : Controller_0897;
            attribute :>> limit = 2.0 [kg];
        }
    }

    package Subsystem_0898 {
        part def Sensor_0898 :> Common::Component {
            attribute :>> mass = 0.23 [kg];
            attribute :>> cost = 48.0;
            attribute range : Real = 148.0;
            port data : Common::DataPort;
        }
        part def Controller_0898 :> Common::Component {
            attribute :>> mass = 1.20 [kg];
            attribute :>> cost = 298.0;
            port supply : Common::PowerPort;
            part sensors : Sensor_0898[2];
            action smooth : Common::Process;
            action forward : Common::Process;
            succession first smooth then forward;
            exhibit state lifecycle : Common::Lifecycle;
        }
        requirement controllerMass_0898 : Common::MassLimit {
            subject component : Controller_0898;
            attribute :>> limit = 2.0 [kg];
        }
    }

    package Subsystem_0899 {
        part def Sensor_0899 :> Common::Component {
            attribute :>> mass = 0.24 [kg];
            attribute :>> cost = 49.0;
            attribute range : Real = 149.0;
            port data : Common::DataPort;
        }
        part def Controller_0899 :> Common::Component {
            attribute :>> mass = 1.30 [kg];
            attribute :>> cost = 299.0;
            port supply : Common::PowerPort;
            part sensors : Sensor_0899[2];
            action smooth : Common::Process;
            action forward : Common::Process;
            succession first smooth then forward;
            exhibit state lifecycle : Common::Lifecycle;
        }
        requirement controllerMass_0899 : Common::MassLimit {
            subject component : Controller_0899;
            attribute :>> limit = 2.0 [kg];
        }
    }

    package Subsystem_0900 {
        part def Sensor_0900 :> Common::Component {
            attribute :>> mass = 0.20 [kg];
            attribute :>> cost = 30.0;
            attribute range : Real = 100.0;
            port data : Common::DataPort;
        }
        part def Controller_0900 :> Common::Component {
            attribute :>> mass = 1.40 [kg];
            attribute :>> cost = 200.0;
            port supply : Common::PowerPort;
            part sensors : Sensor_0900[2];
            action smooth : Common::Process;
            action forward : Common::Process;
            succession first smooth then forward;
            exhibit state lifecycle : Common::Lifecycle;
        }
        requirement controllerMass_0900 : Common::MassLimit {
            subject component : Controller_0900;
            attribute :>> limit = 2.0 [kg];
        }
    }

    package Subsystem_0901 {
        part def Sensor_0901 :> Common::Component {
            attribute :>> mass = 0.21 [kg];
            attribute :>> cost = 31.0;
            attribute range : Real = 101.0;
            port data : Common::DataPort;
        }
        part def Controller_0901 :> Common::Component {
            attribute :>> mass = 1.50 [kg];
            attribute :>> cost = 201.0;
            port supply : Common::PowerPort;
            part sensors : Sensor_0901[2];
            action smooth : Common::Process;
            action forward : Common::Process;
            succession first smooth then forward;
            exhibit state lifecycle : Common::Lifecycle;
        }
        requirement controllerMass_0901 : Common::MassLimit {
            subject component : Controller_0901;
            attribute :>> limit = 2.0 [kg];
        }
    }

    package Subsystem_0902 {
        part def Sensor_0902 :> Common::Component {
            attribute :>> mass = 0.22 [kg];
            attribute :>> cost = 32.0;
            attribute range : Real = 102.0;
            port data : Common::DataPort;
        }
        part def Controller_0902 :> Common::Component {
            attribute :>> mass = 1.60 [kg];
            attribute :>> cost = 202.0;
            port supply : Common::PowerPort;
            part sensors : Sensor_0902[2];
            action smooth : Common::Process;
            action forward : Common::Process;
            succession first smooth then forward;
            exhibit state lifecycle : Common::Lifecycle;
        }
        requirement controllerMass_0902 : Common::MassLimit {
            subject component : Controller_0902;
            attribute :>> limit = 2.0 [kg];
        }
    }

    package Subsystem_0903 {
        part def Sensor_0903 :> Common::Component {
            attribute :>> mass = 0.23 [kg];
            attribute :>> cost = 33.0;
            attribute range : Real = 103.0;
            port data : Common::DataPort;
        }
        part def Controller_0903 :> Common::Component {
            attribute :>> mass = 1.00 [kg];
            attribute :>> cost = 203.0;
            port supply : Common::PowerPort;
            part sensors : Sensor_0903[2];
            action smooth : Common::Process;
            action forward : Common::Process;
            succession first smooth then forward;
            exhibit state lifecycle : Common::Lifecycle;
        }
        requirement controllerMass_0903 : Common::MassLimit {
            subject component : Controller_0903;
            attribute :>> limit = 2.0 [kg];
        }
    }

    package Subsystem_0904 {
        part def Sensor_0904 :> Common::Component {
            attribute :>> mass = 0.24 [kg];
            attribute :>> cost = 34.0;
            attribute range : Real = 104.0;
            port data : Common::DataPort;
        }
        part def Controller_0904 :> Common::Component {
            attribute :>> mass = 1.10 [kg];
            attribute :>> cost = 204.0;
            port supply : Common::PowerPort;
            part sensors : Sensor_0904[2];
            action smooth : Common::Process;
            action forward : Common::Process;
            succession first smooth then forward;
            exhibit state lifecycle : Common::Lifecycle;
        }
        requirement controllerMass_0904 : Common::MassLimit {
            subject component : Controller_0904;
            attribute :>> limit = 2.0 [kg];
        }
    }

    package Subsystem_0905 {
        part def Sensor_0905 :> Common::Component {
            attribute :>> mass = 0.20 [kg];
            attribute :>> cost = 35.0;
            attribute range : Real = 105.0;
            port data : Common::DataPort;
        }
        part def Controller_0905 :> Common::Component {
            attribute :>> mass = 1.20 [kg];
            attribute :>> cost = 205.0;
            port supply : Common::PowerPort;
            part sensors : Sensor_0905[2];
            action smooth : Common::Process;
            action forward : Common::Process;
            succession first smooth then forward;
            exhibit state lifecycle : Common::Lifecycle;
        }
        requirement controllerMass_0905 : Common::MassLimit {
            subject component : Controller_0905;
            attribute :>> limit = 2.0 [kg];
        }
    }

    package Subsystem_0906 {
        part def Sensor_0906 :> Common::Component {
            attribute :>> mass = 0.21 [kg];
            attribute :>> cost = 36.0;
            attribute range : Real = 106.0;
            port data : Common::DataPort;
        }
        part def Controller_0906 :> Common::Component {
            attribute :>> mass = 1.30 [kg];
            attribute :>> cost = 206.0;
            port supply : Common::PowerPort;
            part sensors : Sensor_0906[2];
            action smooth : Common::Process;
            action forward : Common::Process;
            succession first smooth then forward;
            exhibit state lifecycle : Common::Lifecycle;
        }
        requirement controllerMass_0906 : Common::MassLimit {
            subject component : Controller_0906;
            attribute :>> limit = 2.0 [kg];
        }
    }

    package Subsystem_0907 {
        part def Sensor_0907 :> Common::Component {
            attribute :>> mass = 0.22 [kg];
            attribute :>> cost = 37.0;
            attribute range : Real = 107.0;
            port data : Common::DataPort;
        }
        part def Controller_0907 :> Common::Component {
            attribute :>> mass = 1.40 [kg];
            attribute :>> cost = 207.0;
            port supply : Common::PowerPort;
            part sensors : Sensor_0907[2];
            action smooth : Common::Process;
            action forward : Common::Process;
            succession first smooth then forward;
            exhibit state lifecycle : Common::Lifecycle;
        }
        requirement controllerMass_0907 : Common::MassLimit {
            subject component : Controller_0907;
            attribute :>> limit = 2.0 [kg];
        }
    }

    package Subsystem_0908 {
        part def Sensor_0908 :> Common::Component {
            attribute :>> mass = 0.23 [kg];
            attribute :>> cost = 38.0;
            attribute range : Real = 108.0;
            port data : Common::DataPort;
        }
        part def Controller_0908 :> Common::Component {
            attribute :>> mass = 1.50 [kg];
            attribute :>> cost = 208.0;
            port supply : Common::PowerPort;
            part sensors : Sensor_0908[2];
            action smooth : Common::Process;
            action forward : Common::Process;
            succession first smooth then forward;
            exhibit state lifecycle : Common::Lifecycle;
        }
        requirement controllerMass_0908 : Common::MassLimit {
            subject component : Controller_0908;
            attribute :>> limit = 2.0 [kg];
        }
    }

    package Subsystem_0909 {
        part def Sensor_0909 :> Common::Component {
            attribute :>> mass = 0.24 [kg];
            attribute :>> cost = 39.0;
            attribute range : Real = 109.0;
            port data : Common::DataPort;
        }
        part def Controller_0909 :> Common::Component {
            attribute :>> mass = 1.60 [kg];
            attribute :>> cost = 209.0;
            port supply : Common::PowerPort;
            part sensors : Sensor_0909[2];
            action smooth : Common::Process;
            action forward : Common::Process;
            succession first smooth then forward;
            exhibit state lifecycle : Common::Lifecycle;
        }
        requirement controllerMass_0909 : Common::MassLimit {
            subject component : Controller_0909;
            attribute :>> limit = 2.0 [kg];
        }
    }

    package Subsystem_0910 {
        part def Sensor_0910 :> Common::Component {
            attribute :>> mass = 0.20 [kg];
            attribute :>> cost = 40.0;
            attribute range : Real = 110.0;
            port data : Common::DataPort;
        }
        part def Controller_0910 :> Common::Component {
            attribute :>> mass = 1.00 [kg];
            attribute :>> cost = 210.0;
            port supply : Common::PowerPort;
            part sensors : Sensor_0910[2];
            action smooth : Common::Process;
            action forward : Common::Process;
            succession first smooth then forward;
            exhibit state lifecycle : Common::Lifecycle;
        }
        requirement controllerMass_0910 : Common::MassLimit {
            subject component : Controller_0910;
            attribute :>> limit = 2.0 [kg];
        }
    }

    package Subsystem_0911 {
        part def Sensor_0911 :> Common::Component {
            attribute :>> mass = 0.21 [kg];
            attribute :>> cost = 41.0;
            attribute range : Real = 111.0;
            port data : Common::DataPort;
        }
        part def Controller_0911 :> Common::Component {
            attribute :>> mass = 1.10 [kg];
            attribute :>> cost = 211.0;
            port supply : Common::PowerPort;
            part sensors : Sensor_0911[2];
            action smooth : Common::Process;
            action forward : Common::Process;
            succession first smooth then forward;
            exhibit state lifecycle : Common::Lifecycle;
        }
        requirement controllerMass_0911 : Common::MassLimit {
            subject component : Controller_0911;
            attribute :>> limit = 2.0 [kg];
        }
    }

    package Subsystem_0912 {
        part def Sensor_0912 :> Common::Component {
            attribute :>> mass = 0.22 [kg];
            attribute :>> cost = 42.0;
            attribute range : Real = 112.0;
            port data : Common::DataPort;
        }
        part def Controller_0912 :> Common::Component {
            attribute :>> mass = 1.20 [kg];
            attribute :>> cost = 212.0;
            port supply : Common::PowerPort;
            part sensors : Sensor_0912[2];
            action smooth : Common::Process;
            action forward : Common::Process;
            succession first smooth then forward;
            exhibit state lifecycle : Common::Lifecycle;
        }
        requirement controllerMass_0912 : Common::MassLimit {
            subject component : Controller_0912;
            attribute :>> limit = 2.0 [kg];
        }
    }

    package Subsystem_0913 {
        part def Sensor_0913 :> Common::Component {
            attribute :>> mass = 0.23 [kg];
            attribute :>> cost = 43.0;
            attribute range : Real = 113.0;
            port data : Common::DataPort;
        }
        part def Controller_0913 :> Common::Component {
            attribute :>> mass = 1.30 [kg];
            attribute :>> cost = 213.0;
            port supply : Common::PowerPort;
            part sensors : Sensor_0913[2];
            action smooth : Common::Process;
            action forward : Common::Process;
            succession first smooth then forward;
            exhibit state lifecycle : Common::Lifecycle;
        }
        requirement controllerMass_0913 : Common::MassLimit {
            subject component : Controller_0913;
            attribute :>> limit = 2.0 [kg];
        }
    }

    package Subsystem_0914 {
        part def Sensor_0914 :> Common::Component {
            attribute :>> mass = 0.24 [kg];
            attribute :>> cost = 44.0;
            attribute range : Real = 114.0;
            port data : Common::DataPort;
        }
        part def Controller_0914 :> Common::Component {
            attribute :>> mass = 1.40 [kg];
            attribute :>> cost = 214.0;
            port supply : Common::PowerPort;
            part sensors : Sensor_0914[2];
            action smooth : Common::Process;
            action forward : Common::Process;
            succession first smooth then forward;
            exhibit state lifecycle : Common::Lifecycle;
        }
        requirement controllerMass_0914 : Common::MassLimit {
            subject component : Controller_0914;
            attribute :>> limit = 2.0 [kg];
        }
    }

    package Subsystem_0915 {
        part def Sensor_0915 :> Common::Component {
            attribute :>> mass = 0.20 [kg];
            attribute :>> cost = 45.0;
            attribute range : Real = 115.0;
            port data : Common::DataPort;
        }
        part def Controller_0915 :> Common::Component {
            attribute :>> mass = 1.50 [kg];
            attribute :>> cost = 215.0;
            port supply : Common::PowerPort;
            part sensors : Sensor_0915[2];
            action smooth : Common::Process;
            action forward : Common::Process;
            succession first smooth then forward;
            exhibit state lifecycle : Common::Lifecycle;
        }
        requirement controllerMass_0915 : Common::MassLimit {
            subject component : Controller_0915;
            attribute :>> limit = 2.0 [kg];
        }
    }

    package Subsystem_0916 {
        part def Sensor_0916 :> Common::Component {
            attribute :>> mass = 0.21 [kg];
            attribute :>> cost = 46.0;
            attribute range : Real = 116.0;
            port data : Common::DataPort;
        }
        part def Controller_0916 :> Common::Component {
            attribute :>> mass = 1.60 [kg];
            attribute :>> cost = 216.0;
            port supply : Common::PowerPort;
            part sensors : Sensor_0916[2];
            action smooth : Common::Process;
            action forward : Common::Process;
            succession first smooth then forward;
            exhibit state lifecycle : Common::Lifecycle;
        }
        requirement controllerMass_0916 : Common::MassLimit {
            subject component : Controller_0916;
            attribute :>> limit = 2.0 [kg];
        }
    }

    package Subsystem_0917 {
        part def Sensor_0917 :> Common::Component {
            attribute :>> mass = 0.22 [kg];
            attribute :>> cost = 47.0;
            attribute range : Real = 117.0;
            port data : Common::DataPort;
        }
        part def Controller_0917 :> Common::Component {
            attribute :>> mass = 1.00 [kg];
            attribute :>> cost = 217.0;
            port supply : Common::PowerPort;
            part sensors : Sensor_0917[2];
            action smooth : Common::Process;
            action forward : Common::Process;
            succession first smooth then forward;
            exhibit state lifecycle : Common::Lifecycle;
        }
        requirement controllerMass_0917 : Common::MassLimit {
            subject component : Controller_0917;
            attribute :>> limit = 2.0 [kg];
        }
    }

    package Subsystem_0918 {
        part def Sensor_0918 :> Common::Component {
            attribute :>> mass = 0.23 [kg];
            attribute :>> cost = 48.0;
            attribute range : Real = 118.0;
            port data : Common::DataPort;
        }
        part def Controller_0918 :> Common::Component {
            attribute :>> mass = 1.10 [kg];
            attribute :>> cost = 218.0;
            port supply : Common::PowerPort;
            part sensors : Sensor_0918[2];
            action smooth : Common::Process;
            action forward : Common::Process;
            succession first smooth then forward;
            exhibit state lifecycle : Common::Lifecycle;
        }
        requirement controllerMass_0918 : Common::MassLimit {
            subject component : Controller_0918;
            attribute :>> limit = 2.0 [kg];
        }
    }

    package Subsystem_0919 {
        part def Sensor_0919 :> Common::Component {
            attribute :>> mass = 0.24 [kg];
            attribute :>> cost = 49.0;
            attribute range : Real = 119.0;
            port data : Common::DataPort;
        }
        part def Controller_0919 :> Common::Component {
            attribute :>> mass = 1.20 [kg];
            attribute :>> cost = 219.0;
            port supply : Common::PowerPort;
            part sensors : Sensor_0919[2];
            action smooth : Common::Process;
            action forward : Common::Process;
            succession first smooth then forward;
            exhibit state lifecycle : Common::Lifecycle;
        }
        requirement controllerMass_0919 : Common::MassLimit {
            subject component : Controller_0919;
            attribute :>> limit = 2.0 [kg];
        }
    }

    package Subsystem_0920 {
        part def Sensor_0920 :> Common::Component {
            attribute :>> mass = 0.20 [kg];
            attribute :>> cost = 30.0;
            attribute range : Real = 120.0;
            port data : Common::DataPort;
        }
        part def Controller_0920 :> Common::Component {
            attribute :>> mass = 1.30 [kg];
            attribute :>> cost = 220.0;
            port supply : Common::PowerPort;
            part sensors : Sensor_0920[2];
            action smooth : Common::Process;
            action forward : Common::Process;
            succession first smooth then forward;
            exhibit state lifecycle : Common::Lifecycle;
        }
        requirement controllerMass_0920 : Common::MassLimit {
            subject component : Controller_0920;
            attribute :>> limit = 2.0 [kg];
        }
    }

    package Subsystem_0921 {
        part def Sensor_0921 :> Common::Component {
            attribute :>> mass = 0.21 [kg];
            attribute :>> cost = 31.0;
            attribute range : Real = 121.0;
            port data : Common::DataPort;
        }
        part def Controller_0921 :> Common::Component {
            attribute :>> mass = 1.40 [kg];
            attribute :>> cost = 221.0;
            port supply : Common::PowerPort;
            part sensors : Sensor_0921[2];
            action smooth : Common::Process;
            action forward : Common::Process;
            succession first smooth then forward;
            exhibit state lifecycle : Common::Lifecycle;
        }
        requirement controllerMass_0921 : Common::MassLimit {
            subject component : Controller_0921;
            attribute :>> limit = 2.0 [kg];
        }
    }

    package Subsystem_0922 {
        part def Sensor_0922 :> Common::Component {
            attribute :>> mass = 0.22 [kg];
            attribute :>> cost = 32.0;
            attribute range : Real = 122.0;
            port data : Common::DataPort;
        }
        part def Controller_0922 :> Common::Component {
            attribute :>> mass = 1.50 [kg];
            attribute :>> cost = 222.0;
            port supply : Common::PowerPort;
            part sensors : Sensor_0922[2];
            action smooth : Common::Process;
            action forward : Common::Process;
            succession first smooth then forward;
            exhibit state lifecycle : Common::Lifecycle;
        }
        requirement controllerMass_0922 : Common::MassLimit {
            subject component : Controller_0922;
            attribute :>> limit = 2.0 [kg];
        }
    }

    package Subsystem_0923 {
        part def Sensor_0923 :> Common::Component {
            attribute :>> mass = 0.23 [kg];
            attribute :>> cost = 33.0;
            attribute range : Real = 123.0;
            port data : Common::DataPort;
        }
        part def Controller_0923 :> Common::Component {
            attribute :>> mass = 1.60 [kg];
            attribute :>> cost = 223.0;
            port supply : Common::PowerPort;
            part sensors : Sensor_0923[2];
            action smooth : Common::Process;
            action forward : Common::Process;
            succession first smooth then forward;
            exhibit state lifecycle : Common::Lifecycle;
        }
        requirement controllerMass_0923 : Common::MassLimit {
            subject component : Controller_0923;
            attribute :>> limit = 2.0 [kg];
        }
    }

    package Subsystem_0924 {
        part def Sensor_0924 :> Common::Component {
            attribute :>> mass = 0.24 [kg];
            attribute :>> cost = 34.0;
            attribute range : Real = 124.0;
            port data : Common::DataPort;
        }
        part def Controller_0924 :> Common::Component {
            attribute :>> mass = 1.00 [kg];
            attribute :>> cost = 224.0;
            port supply : Common::PowerPort;
            part sensors : Sensor_0924[2];
            action smooth : Common::Process;
            action forward : Common::Process;
            succession first smooth then forward;
            exhibit state lifecycle : Common::Lifecycle;
        }
        requirement controllerMass_0924 : Common::MassLimit {
            subject component : Controller_0924;
            attribute :>> limit = 2.0 [kg];
        }
    }

    package Subsystem_0925 {
        part def Sensor_0925 :> Common::Component {
            attribute :>> mass = 0.20 [kg];
            attribute :>> cost = 35.0;
            attribute range : Real = 125.0;
            port data : Common::DataPort;
        }
        part def Controller_0925 :> Common::Component {
            attribute :>> mass = 1.10 [kg];
            attribute :>> cost = 225.0;
            port supply : Common::PowerPort;
            part sensors : Sensor_0925[2];
            action smooth : Common::Process;
            action forward : Common::Process;
            succession first smooth then forward;
            exhibit state lifecycle : Common::Lifecycle;
        }
        requirement controllerMass_0925 : Common::MassLimit {
            subject component : Controller_0925;
            attribute :>> limit = 2.0 [kg];
        }
    }

    package Subsystem_0926 {
        part def Sensor_0926 :> Common::Component {
            attribute :>> mass = 0.21 [kg];
            attribute :>> cost = 36.0;
            attribute range : Real = 126.0;
            port data : Common::DataPort;
        }
        part def Controller_0926 :> Common::Component {
            attribute :>> mass = 1.20 [kg];
            attribute :>> cost = 226.0;
            port supply : Common::PowerPort;
            part sensors : Sensor_0926[2];
            action smooth : Common::Process;
            action forward : Common::Process;
            succession first smooth then forward;
            exhibit state lifecycle : Common::Lifecycle;
        }
        requirement controllerMass_0926 : Common::MassLimit {
            subject component : Controller_0926;
            attribute :>> limit = 2.0 [kg];
        }
    }

    package Subsystem_0927 {
        part def Sensor_0927 :> Common::Component {
            attribute :>> mass = 0.22 [kg];
            attribute :>> cost = 37.0;
            attribute range : Real = 127.0;
            port data : Common::DataPort;
        }
        part def Controller_0927 :> Common::Component {
            attribute :>> mass = 1.30 [kg];
            attribute :>> cost = 227.0;
            port supply : Common::PowerPort;
            part sensors : Sensor_0927[2];
            action smooth : Common::Process;
            action forward : Common::Process;
            succession first smooth then forward;
            exhibit state lifecycle : Common::Lifecycle;
        }
        requirement controllerMass_0927 : Common::MassLimit {
            subject component : Controller_0927;
            attribute :>> limit = 2.0 [kg];
        }
    }

    package Subsystem_0928 {
        part def Sensor_0928 :> Common::Component {
            attribute :>> mass = 0.23 [kg];
            attribute :>> cost = 38.0;
            attribute range : Real = 128.0;
            port data : Common::DataPort;
        }
        part def Controller_0928 :> Common::Component {
            attribute :>> mass = 1.40 [kg];
            attribute :>> cost = 228.0;
            port supply : Common::PowerPort;
            part sensors : Sensor_0928[2];
            action smooth : Common::Process;
            action forward : Common::Process;
            succession first smooth then forward;
            exhibit state lifecycle : Common::Lifecycle;
        }
        requirement controllerMass_0928 : Common::MassLimit {
            subject component : Controller_0928;
            attribute :>> limit = 2.0 [kg];
        }
    }

    package Subsystem_0929 {
        part def Sensor_0929 :> Common::Component {
            attribute :>> mass = 0.24 [kg];
            attribute :>> cost = 39.0;
            attribute range : Real = 129.0;
            port data : Common::DataPort;
        }
        part def Controller_0929 :> Common::Component {
            attribute :>> mass = 1.50 [kg];
            attribute :>> cost = 229.0;
            port supply : Common::PowerPort;
            part sensors : Sensor_0929[2];
            action smooth : Common::Process;
            action forward : Common::Process;
            succession first smooth then forward;
            exhibit state lifecycle : Common::Lifecycle;
        }
        requirement controllerMass_0929 : Common::MassLimit {
            subject component : Controller_0929;
            attribute :>> limit = 2.0 [kg];
        }
    }

    package Subsystem_0930 {
        part def Sensor_0930 :> Common::Component {
            attribute :>> mass = 0.20 [kg];
            attribute :>> cost = 40.0;
            attribute range : Real = 130.0;
            port data : Common::DataPort;
        }
        part def Controller_0930 :> Common::Component {
            attribute :>> mass = 1.60 [kg];
            attribute :>> cost = 230.0;
            port supply : Common::PowerPort;
            part sensors : Sensor_0930[2];
            action smooth : Common::Process;
            action forward : Common::Process;
            succession first smooth then forward;
            exhibit state lifecycle : Common::Lifecycle;
        }
        requirement controllerMass_0930 : Common::MassLimit {
            subject component : Controller_0930;
            attribute :>> limit = 2.0 [kg];
        }
    }

    package Subsystem_0931 {
        part def Sensor_0931 :> Common::Component {
            attribute :>> mass = 0.21 [kg];
            attribute :>> cost = 41.0;
            attribute range : Real = 131.0;
            port data : Common::DataPort;
        }
        part def Controller_0931 :> Common::Component {
            attribute :>> mass = 1.00 [kg];
            attribute :>> cost = 231.0;
            port supply : Common::PowerPort;
            part sensors : Sensor_0931[2];
            action smooth : Common::Process;
            action forward : Common::Process;
            succession first smooth then forward;
            exhibit state lifecycle : Common::Lifecycle;
        }
        requirement controllerMass_0931 : Common::MassLimit {
            subject component : Controller_0931;
            attribute :>> limit = 2.0 [kg];
        }
    }

    package Subsystem_0932 {
        part def Sensor_0932 :> Common::Component {
            attribute :>> mass = 0.22 [kg];
            attribute :>> cost = 42.0;
            attribute range : Real = 132.0;
            port data : Common::DataPort;
        }
        part def Controller_0932 :> Common::Component {
            attribute :>> mass = 1.10 [kg];
            attribute :>> cost = 232.0;
            port supply : Common::PowerPort;
            part sensors : Sensor_0932[2];
            action smooth : Common::Process;
            action forward : Common::Process;
            succession first smooth then forward;
            exhibit state lifecycle : Common::Lifecycle;
        }
        requirement controllerMass_0932 : Common::MassLimit {
            subject component : Controller_0932;
            attribute :>> limit = 2.0 [kg];
        }
    }

    package Subsystem_0933 {
        part def Sensor_0933 :> Common::Component {
            attribute :>> mass = 0.23 [kg];
            attribute :>> cost = 43.0;
            attribute range : Real = 133.0;
            port data : Common::DataPort;
        }
        part def Controller_0933 :> Common::Component {
            attribute :>> mass = 1.20 [kg];
            attribute :>> cost = 233.0;
            port supply : Common::PowerPort;
            part sensors : Sensor_0933[2];
            action smooth : Common::Process;
            action forward : Common::Process;
            succession first smooth then forward;
            exhibit state lifecycle : Common::Lifecycle;
        }
        requirement controllerMass_0933 : Common::MassLimit {
            subject component : Controller_0933;
            attribute :>> limit = 2.0 [kg];
        }
    }

    package Subsystem_0934 {
        part def Sensor_0934 :> Common::Component {
            attribute :>> mass = 0.24 [kg];
            attribute :>> cost = 44.0;
            attribute range : Real = 134.0;
            port data : Common::DataPort;
        }
        part def Controller_0934 :> Common::Component {
            attribute :>> mass = 1.30 [kg];
            attribute :>> cost = 234.0;
            port supply : Common::PowerPort;
            part sensors : Sensor_0934[2];
            action smooth : Common::Process;
            action forward : Common::Process;
            succession first smooth then forward;
            exhibit state lifecycle : Common::Lifecycle;
        }
        requirement controllerMass_0934 : Common::MassLimit {
            subject component : Controller_0934;
            attribute :>> limit = 2.0 [kg];
        }
    }

    package Subsystem_0935 {
        part def Sensor_0935 :> Common::Component {
            attribute :>> mass = 0.20 [kg];
            attribute :>> cost = 45.0;
            attribute range : Real = 135.0;
            port data : Common::DataPort;
        }
        part def Controller_0935 :> Common::Component {
            attribute :>> mass = 1.40 [kg];
            attribute :>> cost = 235.0;
            port supply : Common::PowerPort;
            part sensors : Sensor_0935[2];
            action smooth : Common::Process;
            action forward : Common::Process;
            succession first smooth then forward;
            exhibit state lifecycle : Common::Lifecycle;
        }
        requirement controllerMass_0935 : Common::MassLimit {
            subject component : Controller_0935;
            attribute :>> limit = 2.0 [kg];
        }
    }

    package Subsystem_0936 {
        part def Sensor_0936 :> Common::Component {
            attribute :>> mass = 0.21 [kg];
            attribute :>> cost = 46.0;
            attribute range : Real = 136.0;
            port data : Common::DataPort;
        }
        part def Controller_0936 :> Common::Component {
            attribute :>> mass = 1.50 [kg];
            attribute :>> cost = 236.0;
            port supply : Common::PowerPort;
            part sensors : Sensor_0936[2];
            action smooth : Common::Process;
            action forward : Common::Process;
            succession first smooth then forward;
            exhibit state lifecycle : Common::Lifecycle;
        }
        requirement controllerMass_0936 : Common::MassLimit {
            subject component : Controller_0936;
            attribute :>> limit = 2.0 [kg];
        }
    }

    package Subsystem_0937 {
        part def Sensor_0937 :> Common::Component {
            attribute :>> mass = 0.22 [kg];
            attribute :>> cost = 47.0;
            attribute range : Real = 137.0;
            port data : Common::DataPort;
        }
        part def Controller_0937 :> Common::Component {
            attribute :>> mass = 1.60 [kg];
            attribute :>> cost = 237.0;
            port supply : Common::PowerPort;
            part sensors : Sensor_0937[2];
            action smooth : Common::Process;
            action forward : Common::Process;
            succession first smooth then forward;
            exhibit state lifecycle : Common::Lifecycle;
        }
        requirement controllerMass_0937 : Common::MassLimit {
            subject component : Controller_0937;
            attribute :>> limit = 2.0 [kg];
        }
    }

    package Subsystem_0938 {
        part def Sensor_0938 :> Common::Component {
            attribute :>> mass = 0.23 [kg];
            attribute :>> cost = 48.0;
            attribute range : Real = 138.0;
            port data : Common::DataPort;
        }
        part def Controller_0938 :> Common::Component {
            attribute :>> mass = 1.00 [kg];
            attribute :>> cost = 238.0;
            port supply : Common::PowerPort;
            part sensors : Sensor_0938[2];
            action smooth : Common::Process;
            action forward : Common::Process;
            succession first smooth then forward;
            exhibit state lifecycle : Common::Lifecycle;
        }
        requirement controllerMass_0938 : Common::MassLimit {
            subject component : Controller_0938;
            attribute :>> limit = 2.0 [kg];
        }
    }

    package Subsystem_0939 {
        part def Sensor_0939 :> Common::Component {
            attribute :>> mass = 0.24 [kg];
            attribute :>> cost = 49.0;
            attribute range : Real = 139.0;
            port data : Common::DataPort;
        }
        part def Controller_0939 :> Common::Component {
            attribute :>> mass = 1.10 [kg];
            attribute :>> cost = 239.0;
            port supply : Common::PowerPort;
            part sensors : Sensor_0939[2];
            action smooth : Common::Process;
            action forward : Common::Process;
            succession first smooth then forward;
            exhibit state lifecycle : Common::Lifecycle;
        }
        requirement controllerMass_0939 : Common::MassLimit {
            subject component : Controller_0939;
            attribute :>> limit = 2.0 [kg];
        }
    }

    package Subsystem_0940 {
        part def Sensor_0940 :> Common::Component {
            attribute :>> mass = 0.20 [kg];
            attribute :>> cost = 30.0;
            attribute range : Real = 140.0;
            port data : Common::DataPort;
        }
        part def Controller_0940 :> Common::Component {
            attribute :>> mass = 1.20 [kg];
            attribute :>> cost = 240.0;
            port supply : Common::PowerPort;
            part sensors : Sensor_0940[2];
            action smooth : Common::Process;
            action forward : Common::Process;
            succession first smooth then forward;
            exhibit state lifecycle : Common::Lifecycle;
        }
        requirement controllerMass_0940 : Common::MassLimit {
            subject component : Controller_0940;
            attribute :>> limit = 2.0 [kg];
        }
    }

    package Subsystem_0941 {
        part def Sensor_0941 :> Common::Component {
            attribute :>> mass = 0.21 [kg];
            attribute :>> cost = 31.0;
            attribute range : Real = 141.0;
            port data : Common::DataPort;
        }
        part def Controller_0941 :> Common::Component {
            attribute :>> mass = 1.30 [kg];
            attribute :>> cost = 241.0;
            port supply : Common::PowerPort;
            part sensors : Sensor_0941[2];
            action smooth : Common::Process;
            action forward : Common::Process;
            succession first smooth then forward;
            exhibit state lifecycle : Common::Lifecycle;
        }
        requirement controllerMass_0941 : Common::MassLimit {
            subject component : Controller_0941;
            attribute :>> limit = 2.0 [kg];
        }
    }

    package Subsystem_0942 {
        part def Sensor_0942 :> Common::Component {
            attribute :>> mass = 0.22 [kg];
            attribute :>> cost = 32.0;
            attribute range : Real = 142.0;
            port data : Common::DataPort;
        }
        part def Controller_0942 :> Common::Component {
            attribute :>> mass = 1.40 [kg];
            attribute :>> cost = 242.0;
            port supply : Common::PowerPort;
            part sensors : Sensor_0942[2];
            action smooth : Common::Process;
            action forward : Common::Process;
            succession first smooth then forward;
            exhibit state lifecycle : Common::Lifecycle;
        }
        requirement controllerMass_0942 : Common::MassLimit {
            subject component : Controller_0942;
            attribute :>> limit = 2.0 [kg];
        }
    }

    package Subsystem_0943 {
        part def Sensor_0943 :> Common::Component {
            attribute :>> mass = 0.23 [kg];
            attribute :>> cost = 33.0;
            attribute range : Real = 143.0;
            port data : Common::DataPort;
        }
        part def Controller_0943 :> Common::Component {
            attribute :>> mass = 1.50 [kg];
            attribute :>> cost = 243.0;
            port supply : Common::PowerPort;
            part sensors : Sensor_0943[2];
            action smooth : Common::Process;
            action forward : Common::Process;
            succession first smooth then forward;
            exhibit state lifecycle : Common::Lifecycle;
        }
        requirement controllerMass_0943 : Common::MassLimit {
            subject component : Controller_0943;
            attribute :>> limit = 2.0 [kg];
        }
    }

    package Subsystem_0944 {
        part def Sensor_0944 :> Common::Component {
            attribute :>> mass = 0.24 [kg];
            attribute :>> cost = 34.0;
            attribute range : Real = 144.0;
            port data : Common::DataPort;
        }
        part def Controller_0944 :> Common::Component {
            attribute :>> mass = 1.60 [kg];
            attribute :>> cost = 244.0;
            port supply : Common::PowerPort;
            part sensors : Sensor_0944[2];
            action smooth : Common::Process;
            action forward : Common::Process;
            succession first smooth then forward;
            exhibit state lifecycle : Common::Lifecycle;
        }
        requirement controllerMass_0944 : Common::MassLimit {
            subject component : Controller_0944;
            attribute :>> limit = 2.0 [kg];
        }
    }

    package Subsystem_0945 {
        part def Sensor_0945 :> Common::Component {
            attribute :>> mass = 0.20 [kg];
            attribute :>> cost = 35.0;
            attribute range : Real = 145.0;
            port data : Common::DataPort;
        }
        part def Controller_0945 :> Common::Component {
            attribute :>> mass = 1.00 [kg];
            attribute :>> cost = 245.0;
            port supply : Common::PowerPort;
            part sensors : Sensor_0945[2];
            action smooth : Common::Process;
            action forward : Common::Process;
            succession first smooth then forward;
            exhibit state lifecycle : Common::Lifecycle;
        }
        requirement controllerMass_0945 : Common::MassLimit {
            subject component : Controller_0945;
            attribute :>> limit = 2.0 [kg];
        }
    }

    package Subsystem_0946 {
        part def Sensor_0946 :> Common::Component {
            attribute :>> mass = 0.21 [kg];
            attribute :>> cost = 36.0;
            attribute range : Real = 146.0;
            port data : Common::DataPort;
        }
        part def Controller_0946 :> Common::Component {
            attribute :>> mass = 1.10 [kg];
            attribute :>> cost = 246.0;
            port supply : Common::PowerPort;
            part sensors : Sensor_0946[2];
            action smooth : Common::Process;
            action forward : Common::Process;
            succession first smooth then forward;
            exhibit state lifecycle : Common::Lifecycle;
        }
        requirement controllerMass_0946 : Common::MassLimit {
            subject component : Controller_0946;
            attribute :>> limit = 2.0 [kg];
        }
    }

    package Subsystem_0947 {
        part def Sensor_0947 :> Common::Component {
            attribute :>> mass = 0.22 [kg];
            attribute :>> cost = 37.0;
            attribute range : Real = 147.0;
            port data : Common::DataPort;
        }
        part def Controller_0947 :> Common::Component {
            attribute :>> mass = 1.20 [kg];
            attribute :>> cost = 247.0;
            port supply : Common::PowerPort;
            part sensors : Sensor_0947[2];
            action smooth : Common::Process;
            action forward : Common::Process;
            succession first smooth then forward;
            exhibit state lifecycle : Common::Lifecycle;
        }
        requirement controllerMass_0947 : Common::MassLimit {
            subject component : Controller_0947;
            attribute :>> limit = 2.0 [kg];
        }
    }

    package Subsystem_0948 {
        part def Sensor_0948 :> Common::Component {
            attribute :>> mass = 0.23 [kg];
            attribute :>> cost = 38.0;
            attribute range : Real = 148.0;
            port data : Common::DataPort;
        }
        part def Controller_0948 :> Common::Component {
            attribute :>> mass = 1.30 [kg];
            attribute :>> cost = 248.0;
            port supply : Common::PowerPort;
            part sensors : Sensor_0948[2];
            action smooth : Common::Process;
            action forward : Common::Process;
            succession first smooth then forward;
            exhibit state lifecycle : Common::Lifecycle;
        }
        requirement controllerMass_0948 : Common::MassLimit {
            subject component : Controller_0948;
            attribute :>> limit = 2.0 [kg];
        }
    }

    package Subsystem_0949 {
        part def Sensor_0949 :> Common::Component {
            attribute :>> mass = 0.24 [kg];
            attribute :>> cost = 39.0;
            attribute range : Real = 149.0;
            port data : Common::DataPort;
        }
        part def Controller_0949 :> Common::Component {
            attribute :>> mass = 1.40 [kg];
            attribute :>> cost = 249.0;
            port supply : Common::PowerPort;
            part sensors : Sensor_0949[2];
            action smooth : Common::Process;
            action forward : Common::Process;
            succession first smooth then forward;
            exhibit state lifecycle : Common::Lifecycle;
        }
        requirement controllerMass_0949 : Common::MassLimit {
            subject component : Controller_0949;
            attribute :>> limit = 2.0 [kg];
        }
    }

    package Subsystem_0950 {
        part def Sensor_0950 :> Common::Component {
            attribute :>> mass = 0.20 [kg];
            attribute :>> cost = 40.0;
            attribute range : Real = 100.0;
            port data : Common::DataPort;
        }
        part def Controller_0950 :> Common::Component {
            attribute :>> mass = 1.50 [kg];
            attribute :>> cost = 250.0;
            port supply : Common::PowerPort;
            part sensors : Sensor_0950[2];
            action smooth : Common::Process;
            action forward : Common::Process;
            succession first smooth then forward;
            exhibit state lifecycle : Common::Lifecycle;
        }
        requirement controllerMass_0950 : Common::MassLimit {
            subject component : Controller_0950;
            attribute :>> limit = 2.0 [kg];
        }
    }

    package Subsystem_0951 {
        part def Sensor_0951 :> Common::Component {
            attribute :>> mass = 0.21 [kg];
            attribute :>> cost = 41.0;
            attribute range : Real = 101.0;
            port data : Common::DataPort;
        }
        part def Controller_0951 :> Common::Component {
            attribute :>> mass = 1.60 [kg];
            attribute :>> cost = 251.0;
            port supply : Common::PowerPort;
            part sensors : Sensor_0951[2];
            action smooth : Common::Process;
            action forward : Common::Process;
            succession first smooth then forward;
            exhibit state lifecycle : Common::Lifecycle;
        }
        requirement controllerMass_0951 : Common::MassLimit {
            subject component : Controller_0951;
            attribute :>> limit = 2.0 [kg];
        }
    }

    package Subsystem_0952 {
        part def Sensor_0952 :> Common::Component {
            attribute :>> mass = 0.22 [kg];
            attribute :>> cost = 42.0;
            attribute range : Real = 102.0;
            port data : Common::DataPort;
        }
        part def Controller_0952 :> Common::Component {
            attribute :>> mass = 1.00 [kg];
            attribute :>> cost = 252.0;
            port supply : Common::PowerPort;
            part sensors : Sensor_0952[2];
            action smooth : Common::Process;
            action forward : Common::Process;
            succession first smooth then forward;
            exhibit state lifecycle : Common::Lifecycle;
        }
        requirement controllerMass_0952 : Common::MassLimit {
            subject component : Controller_0952;
            attribute :>> limit = 2.0 [kg];
        }
    }

    package Subsystem_0953 {
        part def Sensor_0953 :> Common::Component {
            attribute :>> mass = 0.23 [kg];
            attribute :>> cost = 43.0;
            attribute range : Real = 103.0;
            port data : Common::DataPort;
        }
        part def Controller_0953 :> Common::Component {
            attribute :>> mass = 1.10 [kg];
            attribute :>> cost = 253.0;
            port supply : Common::PowerPort;
            part sensors : Sensor_0953[2];
            action smooth : Common::Process;
            action forward : Common::Process;
            succession first smooth then forward;
            exhibit state lifecycle : Common::Lifecycle;
        }
        requirement controllerMass_0953 : Common::MassLimit {
            subject component : Controller_0953;
            attribute :>> limit = 2.0 [kg];
        }
    }

    package Subsystem_0954 {
        part def Sensor_0954 :> Common::Component {
            attribute :>> mass = 0.24 [kg];
            attribute :>> cost = 44.0;
            attribute range : Real = 104.0;
            port data : Common::DataPort;
        }
        part def Controller_0954 :> Common::Component {
            attribute :>> mass = 1.20 [kg];
            attribute :>> cost = 254.0;
            port supply : Common::PowerPort;
            part sensors : Sensor_0954[2];
            action smooth : Common::Process;
            action forward : Common::Process;
            succession first smooth then forward;
            exhibit state lifecycle : Common::Lifecycle;
        }
        requirement controllerMass_0954 : Common::MassLimit {
            subject component : Controller_0954;
            attribute :>> limit = 2.0 [kg];
        }
    }

    package Subsystem_0955 {
        part def Sensor_0955 :> Common::Component {
            attribute :>> mass = 0.20 [kg];
            attribute :>> cost = 45.0;
            attribute range : Real = 105.0;
            port data : Common::DataPort;
        }
        part def Controller_0955 :> Common::Component {
            attribute :>> mass = 1.30 [kg];
            attribute :>> cost = 255.0;
            port supply : Common::PowerPort;
            part sensors : Sensor_0955[2];
            action smooth : Common::Process;
            action forward : Common::Process;
            succession first smooth then forward;
            exhibit state lifecycle : Common::Lifecycle;
        }
        requirement controllerMass_0955 : Common::MassLimit {
            subject component : Controller_0955;
            attribute :>> limit = 2.0 [kg];
        }
    }

    package Subsystem_0956 {
        part def Sensor_0956 :> Common::Component {
            attribute :>> mass = 0.21 [kg];
            attribute :>> cost = 46.0;
            attribute range : Real = 106.0;
            port data : Common::DataPort;
        }
        part def Controller_0956 :> Common::Component {
            attribute :>> mass = 1.40 [kg];
            attribute :>> cost = 256.0;
            port supply : Common::PowerPort;
            part sensors : Sensor_0956[2];
            action smooth : Common::Process;
            action forward : Common::Process;
            succession first smooth then forward;
            exhibit state lifecycle : Common::Lifecycle;
        }
        requirement controllerMass_0956 : Common::MassLimit {
            subject component : Controller_0956;
            attribute :>> limit = 2.0 [kg];
        }
    }

    package Subsystem_0957 {
        part def Sensor_0957 :> Common::Component {
            attribute :>> mass = 0.22 [kg];
            attribute :>> cost = 47.0;
            attribute range : Real = 107.0;
            port data : Common::DataPort;
        }
        part def Controller_0957 :> Common::Component {
            attribute :>> mass = 1.50 [kg];
            attribute :>> cost = 257.0;
            port supply : Common::PowerPort;
            part sensors : Sensor_0957[2];
            action smooth : Common::Process;
            action forward : Common::Process;
            succession first smooth then forward;
            exhibit state lifecycle : Common::Lifecycle;
        }
        requirement controllerMass_0957 : Common::MassLimit {
            subject component : Controller_0957;
            attribute :>> limit = 2.0 [kg];
        }
    }

    package Subsystem_0958 {
        part def Sensor_0958 :> Common::Component {
            attribute :>> mass = 0.23 [kg];
            attribute :>> cost = 48.0;
            attribute range : Real = 108.0;
            port data : Common::DataPort;
        }
        part def Controller_0958 :> Common::Component {
            attribute :>> mass = 1.60 [kg];
            attribute :>> cost = 258.0;
            port supply : Common::PowerPort;
            part sensors : Sensor_0958[2];
            action smooth : Common::Process;
            action forward : Common::Process;
            succession first smooth then forward;
            exhibit state lifecycle : Common::Lifecycle;
        }
        requirement controllerMass_0958 : Common::MassLimit {
            subject component : Controller_0958;
            attribute :>> limit = 2.0 [kg];
        }
    }

    package Subsystem_0959 {
        part def Sensor_0959 :> Common::Component {
            attribute :>> mass = 0.24 [kg];
            attribute :>> cost = 49.0;
            attribute range : Real = 109.0;
            port data : Common::DataPort;
        }
        part def Controller_0959 :> Common::Component {
            attribute :>> mass = 1.00 [kg];
            attribute :>> cost = 259.0;
            port supply : Common::PowerPort;
            part sensors : Sensor_0959[2];
            action smooth : Common::Process;
            action forward : Common::Process;
            succession first smooth then forward;
            exhibit state lifecycle : Common::Lifecycle;
        }
        requirement controllerMass_0959 : Common::MassLimit {
            subject component : Controller_0959;
            attribute :>> limit = 2.0 [kg];
        }
    }

    package Subsystem_0960 {
        part def Sensor_0960 :> Common::Component {
            attribute :>> mass = 0.20 [kg];
            attribute :>> cost = 30.0;
            attribute range : Real = 110.0;
            port data : Common::DataPort;
        }
        part def Controller_0960 :> Common::Component {
            attribute :>> mass = 1.10 [kg];
            attribute :>> cost = 260.0;
            port supply : Common::PowerPort;
            part sensors : Sensor_0960[2];
            action smooth : Common::Process;
            action forward : Common::Process;
            succession first smooth then forward;
            exhibit state lifecycle : Common::Lifecycle;
        }
        requirement controllerMass_0960 : Common::MassLimit {
            subject component : Controller_0960;
            attribute :>> limit = 2.0 [kg];
        }
    }

    package Subsystem_0961 {
        part def Sensor_0961 :> Common::Component {
            attribute :>> mass = 0.21 [kg];
            attribute :>> cost = 31.0;
            attribute range : Real = 111.0;
            port data : Common::DataPort;
        }
        part def Controller_0961 :> Common::Component {
            attribute :>> mass = 1.20 [kg];
            attribute :>> cost = 261.0;
            port supply : Common::PowerPort;
            part sensors : Sensor_0961[2];
            action smooth : Common::Process;
            action forward : Common::Process;
            succession first smooth then forward;
            exhibit state lifecycle : Common::Lifecycle;
        }
        requirement controllerMass_0961 : Common::MassLimit {
            subject component : Controller_0961;
            attribute :>> limit = 2.0 [kg];
        }
    }

    package Subsystem_0962 {
        part def Sensor_0962 :> Common::Component {
            attribute :>> mass = 0.22 [kg];
            attribute :>> cost = 32.0;
            attribute range : Real = 112.0;
            port data : Common::DataPort;
        }
        part def Controller_0962 :> Common::Component {
            attribute :>> mass = 1.30 [kg];
            attribute :>> cost = 262.0;
            port supply : Common::PowerPort;
            part sensors : Sensor_0962[2];
            action smooth : Common::Process;
            action forward : Common::Process;
            succession first smooth then forward;
            exhibit state lifecycle : Common::Lifecycle;
        }
        requirement controllerMass_0962 : Common::MassLimit {
            subject component : Controller_0962;
            attribute :>> limit = 2.0 [kg];
        }
    }

    package Subsystem_0963 {
        part def Sensor_0963 :> Common::Component {
            attribute :>> mass = 0.23 [kg];
            attribute :>> cost = 33.0;
            attribute range : Real = 113.0;
            port data : Common::DataPort;
        }
        part def Controller_0963 :> Common::Component {
            attribute :>> mass = 1.40 [kg];
            attribute :>> cost = 263.0;
            port supply : Common::PowerPort;
            part sensors : Sensor_0963[2];
            action smooth : Common::Process;
            action forward : Common::Process;
            succession first smooth then forward;
            exhibit state lifecycle : Common::Lifecycle;
        }
        requirement controllerMass_0963 : Common::MassLimit {
            subject component : Controller_0963;
            attribute :>> limit = 2.0 [kg];
        }
    }

    package Subsystem_0964 {
        part def Sensor_0964 :> Common::Component {
            attribute :>> mass = 0.24 [kg];
            attribute :>> cost = 34.0;
            attribute range : Real = 114.0;
            port data : Common::DataPort;
        }
        part def Controller_0964 :> Common::Component {
            attribute :>> mass = 1.50 [kg];
            attribute :>> cost = 264.0;
            port supply : Common::PowerPort;
            part sensors : Sensor_0964[2];
            action smooth : Common::Process;
            action forward : Common::Process;
            succession first smooth then forward;
            exhibit state lifecycle : Common::Lifecycle;
        }
        requirement controllerMass_0964 : Common::MassLimit {
            subject component : Controller_0964;
            attribute :>> limit = 2.0 [kg];
        }
    }

    package Subsystem_0965 {
        part def Sensor_0965 :> Common::Component {
            attribute :>> mass = 0.20 [kg];
            attribute :>> cost = 35.0;
            attribute range : Real = 115.0;
            port data : Common::DataPort;
        }
        part def Controller_0965 :> Common::Component {
            attribute :>> mass = 1.60 [kg];
            attribute :>> cost = 265.0;
            port supply : Common::PowerPort;
            part sensors : Sensor_0965[2];
            action smooth : Common::Process;
            action forward : Common::Process;
            succession first smooth then forward;
            exhibit state lifecycle : Common::Lifecycle;
        }
        requirement controllerMass_0965 : Common::MassLimit {
            subject component : Controller_0965;
            attribute :>> limit = 2.0 [kg];
        }
    }

    package Subsystem_0966 {
        part def Sensor_0966 :> Common::Component {
            attribute :>> mass = 0.21 [kg];
            attribute :>> cost = 36.0;
            attribute range : Real = 116.0;
            port data : Common::DataPort;
        }
        part def Controller_0966 :> Common::Component {
            attribute :>> mass = 1.00 [kg];
            attribute :>> cost = 266.0;
            port supply : Common::PowerPort;
            part sensors : Sensor_0966[2];
            action smooth : Common::Process;
            action forward : Common::Process;
            succession first smooth then forward;
            exhibit state lifecycle : Common::Lifecycle;
        }
        requirement controllerMass_0966 : Common::MassLimit {
            subject component : Controller_0966;
            attribute :>> limit = 2.0 [kg];
        }
    }

    package Subsystem_0967 {
        part def Sensor_0967 :> Common::Component {
            attribute :>> mass = 0.22 [kg];
            attribute :>> cost = 37.0;
            attribute range : Real = 117.0;
            port data : Common::DataPort;
        }
        part def Controller_0967 :> Common::Component {
            attribute :>> mass = 1.10 [kg];
            attribute :>> cost = 267.0;
            port supply : Common::PowerPort;
            part sensors : Sensor_0967[2];
            action smooth : Common::Process;
            action forward : Common::Process;
            succession first smooth then forward;
            exhibit state lifecycle : Common::Lifecycle;
        }
        requirement controllerMass_0967 : Common::MassLimit {
            subject component : Controller_0967;
            attribute :>> limit = 2.0 [kg];
        }
    }

    package Subsystem_0968 {
        part def Sensor_0968 :> Common::Component {
            attribute :>> mass = 0.23 [kg];
            attribute :>> cost = 38.0;
            attribute range : Real = 118.0;
            port data : Common::DataPort;
        }
        part def Controller_0968 :> Common::Component {
            attribute :>> mass = 1.20 [kg];
            attribute :>> cost = 268.0;
            port supply : Common::PowerPort;
            part sensors : Sensor_0968[2];
            action smooth : Common::Process;
            action forward : Common::Process;
            succession first smooth then forward;
            exhibit state lifecycle : Common::Lifecycle;
        }
        requirement controllerMass_0968 : Common::MassLimit {
            subject component : Controller_0968;
            attribute :>> limit = 2.0 [kg];
        }
    }

    package Subsystem_0969 {
        part def Sensor_0969 :> Common::Component {
            attribute :>> mass = 0.24 [kg];
            attribute :>> cost = 39.0;
            attribute range : Real = 119.0;
            port data : Common::DataPort;
        }
        part def Controller_0969 :> Common::Component {
            attribute :>> mass = 1.30 [kg];
            attribute :>> cost = 269.0;
            port supply : Common::PowerPort;
            part sensors : Sensor_0969[2];
            action smooth : Common::Process;
            action forward : Common::Process;
            succession first smooth then forward;
            exhibit state lifecycle : Common::Lifecycle;
        }
        requirement controllerMass_0969 : Common::MassLimit {
            subject component : Controller_0969;
            attribute :>> limit = 2.0 [kg];
        }
    }

    package Subsystem_0970 {
        part def Sensor_0970 :> Common::Component {
            attribute :>> mass = 0.20 [kg];
            attribute :>> cost = 40.0;
            attribute range : Real = 120.0;
            port data : Common::DataPort;
        }
        part def Controller_0970 :> Common::Component {
            attribute :>> mass = 1.40 [kg];
            attribute :>> cost = 270.0;
            port supply : Common::PowerPort;
            part sensors : Sensor_0970[2];
            action smooth : Common::Process;
            action forward : Common::Process;
            succession first smooth then forward;
            exhibit state lifecycle : Common::Lifecycle;
        }
        requirement controllerMass_0970 : Common::MassLimit {
            subject component : Controller_0970;
            attribute :>> limit = 2.0 [kg];
        }
    }

    package Subsystem_0971 {
        part def Sensor_0971 :> Common::Component {
            attribute :>> mass = 0.21 [kg];
            attribute :>> cost = 41.0;
            attribute range : Real = 121.0;
            port data : Common::DataPort;
        }
        part def Controller_0971 :> Common::Component {
            attribute :>> mass = 1.50 [kg];
            attribute :>> cost = 271.0;
            port supply : Common::PowerPort;
            part sensors : Sensor_0971[2];
            action smooth : Common::Process;
            action forward : Common::Process;
            succession first smooth then forward;
            exhibit state lifecycle : Common::Lifecycle;
        }
        requirement controllerMass_0971 : Common::MassLimit {
            subject component : Controller_0971;
            attribute :>> limit = 2.0 [kg];
        }
    }

    package Subsystem_0972 {
        part def Sensor_0972 :> Common::Component {
            attribute :>> mass = 0.22 [kg];
            attribute :>> cost = 42.0;
            attribute range : Real = 122.0;
            port data : Common::DataPort;
        }
        part def Controller_0972 :> Common::Component {
            attribute :>> mass = 1.60 [kg];
            attribute :>> cost = 272.0;
            port supply : Common::PowerPort;
            part sensors : Sensor_0972[2];
            action smooth : Common::Process;
            action forward : Common::Process;
            succession first smooth then forward;
            exhibit state lifecycle : Common::Lifecycle;
        }
        requirement controllerMass_0972 : Common::MassLimit {
            subject component : Controller_0972;
            attribute :>> limit = 2.0 [kg];
        }
    }

    package Subsystem_0973 {
        part def Sensor_0973 :> Common::Component {
            attribute :>> mass = 0.23 [kg];
            attribute :>> cost = 43.0;
            attribute range : Real = 123.0;
            port data : Common::DataPort;
        }
        part def Controller_0973 :> Common::Component {
            attribute :>> mass = 1.00 [kg];
            attribute :>> cost = 273.0;
            port supply : Common::PowerPort;
            part sensors : Sensor_0973[2];
            action smooth : Common::Process;
            action forward : Common::Process;
            succession first smooth then forward;
            exhibit state lifecycle : Common::Lifecycle;
        }
        requirement controllerMass_0973 : Common::MassLimit {
            subject component : Controller_0973;
            attribute :>> limit = 2.0 [kg];
        }
    }

    package Subsystem_0974 {
        part def Sensor_0974 :> Common::Component {
            attribute :>> mass = 0.24 [kg];
            attribute :>> cost = 44.0;
            attribute range : Real = 124.0;
            port data : Common::DataPort;
        }
        part def Controller_0974 :> Common::Component {
            attribute :>> mass = 1.10 [kg];
            attribute :>> cost = 274.0;
            port supply : Common::PowerPort;
            part sensors : Sensor_0974[2];
            action smooth : Common::Process;
            action forward : Common::Process;
            succession first smooth then forward;
            exhibit state lifecycle : Common::Lifecycle;
        }
        requirement controllerMass_0974 : Common::MassLimit {
            subject component : Controller_0974;
            attribute :>> limit = 2.0 [kg];
        }
    }

    package Subsystem_0975 {
        part def Sensor_0975 :> Common::Component {
            attribute :>> mass = 0.20 [kg];
            attribute :>> cost = 45.0;
            attribute range : Real = 125.0;
            port data : Common::DataPort;
        }
        part def Controller_0975 :> Common::Component {
            attribute :>> mass = 1.20 [kg];
            attribute :>> cost = 275.0;
            port supply : Common::PowerPort;
            part sensors : Sensor_0975[2];
            action smooth : Common::Process;
            action forward : Common::Process;
            succession first smooth then forward;
            exhibit state lifecycle : Common::Lifecycle;
        }
        requirement controllerMass_0975 : Common::MassLimit {
            subject component : Controller_0975;
            attribute :>> limit = 2.0 [kg];
        }
    }

    package Subsystem_0976 {
        part def Sensor_0976 :> Common::Component {
            attribute :>> mass = 0.21 [kg];
            attribute :>> cost = 46.0;
            attribute range : Real = 126.0;
            port data : Common::DataPort;
        }
        part def Controller_0976 :> Common::Component {
            attribute :>> mass = 1.30 [kg];
            attribute :>> cost = 276.0;
            port supply : Common::PowerPort;
            part sensors : Sensor_0976[2];
            action smooth : Common::Process;
            action forward : Common::Process;
            succession first smooth then forward;
            exhibit state lifecycle : Common::Lifecycle;
        }
        requirement controllerMass_0976 : Common::MassLimit {
            subject component : Controller_0976;
            attribute :>> limit = 2.0 [kg];
        }
    }

    package Subsystem_0977 {
        part def Sensor_0977 :> Common::Component {
            attribute :>> mass = 0.22 [kg];
            attribute :>> cost = 47.0;
            attribute range : Real = 127.0;
            port data : Common::DataPort;
        }
        part def Controller_0977 :> Common::Component {
            attribute :>> mass = 1.40 [kg];
            attribute :>> cost = 277.0;
            port supply : Common::PowerPort;
            part sensors : Sensor_0977[2];
            action smooth : Common::Process;
            action forward : Common::Process;
            succession first smooth then forward;
            exhibit state lifecycle : Common::Lifecycle;
        }
        requirement controllerMass_0977 : Common::MassLimit {
            subject component : Controller_0977;
            attribute :>> limit = 2.0 [kg];
        }
    }

    package Subsystem_0978 {
        part def Sensor_0978 :> Common::Component {
            attribute :>> mass = 0.23 [kg];
            attribute :>> cost = 48.0;
            attribute range : Real = 128.0;
            port data : Common::DataPort;
        }
        part def Controller_0978 :> Common::Component {
            attribute :>> mass = 1.50 [kg];
            attribute :>> cost = 278.0;
            port supply : Common::PowerPort;
            part sensors : Sensor_0978[2];
            action smooth : Common::Process;
            action forward : Common::Process;
            succession first smooth then forward;
            exhibit state lifecycle : Common::Lifecycle;
        }
        requirement controllerMass_0978 : Common::MassLimit {
            subject component : Controller_0978;
            attribute :>> limit = 2.0 [kg];
        }
    }

    package Subsystem_0979 {
        part def Sensor_0979 :> Common::Component {
            attribute :>> mass = 0.24 [kg];
            attribute :>> cost = 49.0;
            attribute range : Real = 129.0;
            port data : Common::DataPort;
        }
        part def Controller_0979 :> Common::Component {
            attribute :>> mass = 1.60 [kg];
            attribute :>> cost = 279.0;
            port supply : Common::PowerPort;
            part sensors : Sensor_0979[2];
            action smooth : Common::Process;
            action forward : Common::Process;
            succession first smooth then forward;
            exhibit state lifecycle : Common::Lifecycle;
        }
        requirement controllerMass_0979 : Common::MassLimit {
            subject component : Controller_0979;
            attribute :>> limit = 2.0 [kg];
        }
    }

    package Subsystem_0980 {
        part def Sensor_0980 :> Common::Component {
            attribute :>> mass = 0.20 [kg];
            attribute :>> cost = 30.0;
            attribute range : Real = 130.0;
            port data : Common::DataPort;
        }
        part def Controller_0980 :> Common::Component {
            attribute :>> mass = 1.00 [kg];
            attribute :>> cost = 280.0;
            port supply : Common::PowerPort;
            part sensors : Sensor_0980[2];
            action smooth : Common::Process;
            action forward : Common::Process;
            succession first smooth then forward;
            exhibit state lifecycle : Common::Lifecycle;
        }
        requirement controllerMass_0980 : Common::MassLimit {
            subject component : Controller_0980;
            attribute :>> limit = 2.0 [kg];
        }
    }

    package Subsystem_0981 {
        part def Sensor_0981 :> Common::Component {
            attribute :>> mass = 0.21 [kg];
            attribute :>> cost = 31.0;
            attribute range : Real = 131.0;
            port data : Common::DataPort;
        }
        part def Controller_0981 :> Common::Component {
            attribute :>> mass = 1.10 [kg];
            attribute :>> cost = 281.0;
            port supply : Common::PowerPort;
            part sensors : Sensor_0981[2];
            action smooth : Common::Process;
            action forward : Common::Process;
            succession first smooth then forward;
            exhibit state lifecycle : Common::Lifecycle;
        }
        requirement controllerMass_0981 : Common::MassLimit {
            subject component : Controller_0981;
            attribute :>> limit = 2.0 [kg];
        }
    }

    package Subsystem_0982 {
        part def Sensor_0982 :> Common::Component {
            attribute :>> mass = 0.22 [kg];
            attribute :>> cost = 32.0;
            attribute range : Real = 132.0;
            port data : Common::DataPort;
        }
        part def Controller_0982 :> Common::Component {
            attribute :>> mass = 1.20 [kg];
            attribute :>> cost = 282.0;
            port supply : Common::PowerPort;
            part sensors : Sensor_0982[2];
            action smooth : Common::Process;
            action forward : Common::Process;
            succession first smooth then forward;
            exhibit state lifecycle : Common::Lifecycle;
        }
        requirement controllerMass_0982 : Common::MassLimit {
            subject component : Controller_0982;
            attribute :>> limit = 2.0 [kg];
        }
    }

    package Subsystem_0983 {
        part def Sensor_0983 :> Common::Component {
            attribute :>> mass = 0.23 [kg];
            attribute :>> cost = 33.0;
            attribute range : Real = 133.0;
            port data : Common::DataPort;
        }
        part def Controller_0983 :> Common::Component {
            attribute :>> mass = 1.30 [kg];
            attribute :>> cost = 283.0;
            port supply : Common::PowerPort;
            part sensors : Sensor_0983[2];
            action smooth : Common::Process;
            action forward : Common::Process;
            succession first smooth then forward;
            exhibit state lifecycle : Common::Lifecycle;
        }
        requirement controllerMass_0983 : Common::MassLimit {
            subject component : Controller_0983;
            attribute :>> limit = 2.0 [kg];
        }
    }

    package Subsystem_0984 {
        part def Sensor_0984 :> Common::Component {
            attribute :>> mass = 0.24 [kg];
            attribute :>> cost = 34.0;
            attribute range : Real = 134.0;
            port data : Common::DataPort;
        }
        part def Controller_0984 :> Common::Component {
            attribute :>> mass = 1.40 [kg];
            attribute :>> cost = 284.0;
            port supply : Common::PowerPort;
            part sensors : Sensor_0984[2];
            action smooth : Common::Process;
            action forward : Common::Process;
            succession first smooth then forward;
            exhibit state lifecycle : Common::Lifecycle;
        }
        requirement controllerMass_0984 : Common::MassLimit {
            subject component : Controller_0984;
            attribute :>> limit = 2.0 [kg];
        }
    }

    package Subsystem_0985 {
        part def Sensor_0985 :> Common::Component {
            attribute :>> mass = 0.20 [kg];
            attribute :>> cost = 35.0;
            attribute range : Real = 135.0;
            port data : Common::DataPort;
        }
        part def Controller_0985 :> Common::Component {
            attribute :>> mass = 1.50 [kg];
            attribute :>> cost = 285.0;
            port supply : Common::PowerPort;
            part sensors : Sensor_0985[2];
            action smooth : Common::Process;
            action forward : Common::Process;
            succession first smooth then forward;
            exhibit state lifecycle : Common::Lifecycle;
        }
        requirement controllerMass_0985 : Common::MassLimit {
            subject component : Controller_0985;
            attribute :>> limit = 2.0 [kg];
        }
    }

    package Subsystem_0986 {
        part def Sensor_0986 :> Common::Component {
            attribute :>> mass = 0.21 [kg];
            attribute :>> cost = 36.0;
            attribute range : Real = 136.0;
            port data : Common::DataPort;
        }
        part def Controller_0986 :> Common::Component {
            attribute :>> mass = 1.60 [kg];
            attribute :>> cost = 286.0;
            port supply : Common::PowerPort;
            part sensors : Sensor_0986[2];
            action smooth : Common::Process;
            action forward : Common::Process;
            succession first smooth then forward;
            exhibit state lifecycle : Common::Lifecycle;
        }
        requirement controllerMass_0986 : Common::MassLimit {
            subject component : Controller_0986;
            attribute :>> limit = 2.0 [kg];
        }
    }

    package Subsystem_0987 {
        part def Sensor_0987 :> Common::Component {
            attribute :>> mass = 0.22 [kg];
            attribute :>> cost = 37.0;
            attribute range : Real = 137.0;
            port data : Common::DataPort;
        }
        part def Controller_0987 :> Common::Component {
            attribute :>> mass = 1.00 [kg];
            attribute :>> cost = 287.0;
            port supply : Common::PowerPort;
            part sensors : Sensor_0987[2];
            action smooth : Common::Process;
            action forward : Common::Process;
            succession first smooth then forward;
            exhibit state lifecycle : Common::Lifecycle;
        }
        requirement controllerMass_0987 : Common::MassLimit {
            subject component : Controller_0987;
            attribute :>> limit = 2.0 [kg];
        }
    }

    package Subsystem_0988 {
        part def Sensor_0988 :> Common::Component {
            attribute :>> mass = 0.23 [kg];
            attribute :>> cost = 38.0;
            attribute range : Real = 138.0;
            port data : Common::DataPort;
        }
        part def Controller_0988 :> Common::Component {
            attribute :>> mass = 1.10 [kg];
            attribute :>> cost = 288.0;
            port supply : Common::PowerPort;
            part sensors : Sensor_0988[2];
            action smooth : Common::Process;
            action forward : Common::Process;
            succession first smooth then forward;
            exhibit state lifecycle : Common::Lifecycle;
        }
        requirement controllerMass_0988 : Common::MassLimit {
            subject component : Controller_0988;
            attribute :>> limit = 2.0 [kg];
        }
    }

    package Subsystem_0989 {
        part def Sensor_0989 :> Common::Component {
            attribute :>> mass = 0.24 [kg];
            attribute :>> cost = 39.0;
            attribute range : Real = 139.0;
            port data : Common::DataPort;
        }
        part def Controller_0989 :> Common::Component {
            attribute :>> mass = 1.20 [kg];
            attribute :>> cost = 289.0;
            port supply : Common::PowerPort;
            part sensors : Sensor_0989[2];
            action smooth : Common::Process;
            action forward : Common::Process;
            succession first smooth then forward;
            exhibit state lifecycle : Common::Lifecycle;
        }
        requirement controllerMass_0989 : Common::MassLimit {
            subject component : Controller_0989;
            attribute :>> limit = 2.0 [kg];
        }
    }

    package Subsystem_0990 {
        part def Sensor_0990 :> Common::Component {
            attribute :>> mass = 0.20 [kg];
            attribute :>> cost = 40.0;
            attribute range : Real = 140.0;
            port data : Common::DataPort;
        }
        part def Controller_0990 :> Common::Component {
            attribute :>> mass = 1.30 [kg];
            attribute :>> cost = 290.0;
            port supply : Common::PowerPort;
            part sensors : Sensor_0990[2];
            action smooth : Common::Process;
            action forward : Common::Process;
            succession first smooth then forward;
            exhibit state lifecycle : Common::Lifecycle;
        }
        requirement controllerMass_0990 : Common::MassLimit {
            subject component : Controller_0990;
            attribute :>> limit = 2.0 [kg];
        }
    }

    package Subsystem_0991 {
        part def Sensor_0991 :> Common::Component {
            attribute :>> mass = 0.21 [kg];
            attribute :>> cost = 41.0;
            attribute range : Real = 141.0;
            port data : Common::DataPort;
        }
        part def Controller_0991 :> Common::Component {
            attribute :>> mass = 1.40 [kg];
            attribute :>> cost = 291.0;
            port supply : Common::PowerPort;
            part sensors : Sensor_0991[2];
            action smooth : Common::Process;
            action forward : Common::Process;
            succession first smooth then forward;
            exhibit state lifecycle : Common::Lifecycle;
        }
        requirement controllerMass_0991 : Common::MassLimit {
            subject component : Controller_0991;
            attribute :>> limit = 2.0 [kg];
        }
    }

    package Subsystem_0992 {
        part def Sensor_0992 :> Common::Component {
            attribute :>> mass = 0.22 [kg];
            attribute :>> cost = 42.0;
            attribute range : Real = 142.0;
            port data : Common::DataPort;
        }
        part def Controller_0992 :> Common::Component {
            attribute :>> mass = 1.50 [kg];
            attribute :>> cost = 292.0;
            port supply : Common::PowerPort;
            part sensors : Sensor_0992[2];
            action smooth : Common::Process;
            action forward : Common::Process;
            succession first smooth then forward;
            exhibit state lifecycle : Common::Lifecycle;
        }
        requirement controllerMass_0992 : Common::MassLimit {
            subject component : Controller_0992;
            attribute :>> limit = 2.0 [kg];
        }
    }

    package Subsystem_0993 {
        part def Sensor_0993 :> Common::Component {
            attribute :>> mass = 0.23 [kg];
            attribute :>> cost = 43.0;
            attribute range : Real = 143.0;
            port data : Common::DataPort;
        }
        part def Controller_0993 :> Common::Component {
            attribute :>> mass = 1.60 [kg];
            attribute :>> cost = 293.0;
            port supply : Common::PowerPort;
            part sensors : Sensor_0993[2];
            action smooth : Common::Process;
            action forward : Common::Process;
            succession first smooth then forward;
            exhibit state lifecycle : Common::Lifecycle;
        }
        requirement controllerMass_0993 : Common::MassLimit {
            subject component : Controller_0993;
            attribute :>> limit = 2.0 [kg];
        }
    }

    package Subsystem_0994 {
        part def Sensor_0994 :> Common::Component {
            attribute :>> mass = 0.24 [kg];
            attribute :>> cost = 44.0;
            attribute range : Real = 144.0;
            port data : Common::DataPort;
        }
        part def Controller_0994 :> Common::Component {
            attribute :>> mass = 1.00 [kg];
            attribute :>> cost = 294.0;
            port supply : Common::PowerPort;
            part sensors : Sensor_0994[2];
            action smooth : Common::Process;
            action forward : Common::Process;
            succession first smooth then forward;
            exhibit state lifecycle : Common::Lifecycle;
        }
        requirement controllerMass_0994 : Common::MassLimit {
            subject component : Controller_0994;
            attribute :>> limit = 2.0 [kg];
        }
    }

    package Subsystem_0995 {
        part def Sensor_0995 :> Common::Component {
            attribute :>> mass = 0.20 [kg];
            attribute :>> cost = 45.0;
            attribute range : Real = 145.0;
            port data : Common::DataPort;
        }
        part def Controller_0995 :> Common::Component {
            attribute :>> mass = 1.10 [kg];
            attribute :>> cost = 295.0;
            port supply : Common::PowerPort;
            part sensors : Sensor_0995[2];
            action smooth : Common::Process;
            action forward : Common::Process;
            succession first smooth then forward;
            exhibit state lifecycle : Common::Lifecycle;
        }
        requirement controllerMass_0995 : Common::MassLimit {
            subject component : Controller_0995;
            attribute :>> limit = 2.0 [kg];
        }
    }

    package Subsystem_0996 {
        part def Sensor_0996 :> Common::Component {
            attribute :>> mass = 0.21 [kg];
            attribute :>> cost = 46.0;
            attribute range : Real = 146.0;
            port data : Common::DataPort;
        }
        part def Controller_0996 :> Common::Component {
            attribute :>> mass = 1.20 [kg];
            attribute :>> cost = 296.0;
            port supply : Common::PowerPort;
            part sensors : Sensor_0996[2];
            action smooth : Common::Process;
            action forward : Common::Process;
            succession first smooth then forward;
            exhibit state lifecycle : Common::Lifecycle;
        }
        requirement controllerMass_0996 : Common::MassLimit {
            subject component : Controller_0996;
            attribute :>> limit = 2.0 [kg];
        }
    }

    package Subsystem_0997 {
        part def Sensor_0997 :> Common::Component {
            attribute :>> mass = 0.22 [kg];
            attribute :>> cost = 47.0;
            attribute range : Real = 147.0;
            port data : Common::DataPort;
        }
        part def Controller_0997 :> Common::Component {
            attribute :>> mass = 1.30 [kg];
            attribute :>> cost = 297.0;
            port supply : Common::PowerPort;
            part sensors : Sensor_0997[2];
            action smooth : Common::Process;
            action forward : Common::Process;
            succession first smooth then forward;
            exhibit state lifecycle : Common::Lifecycle;
        }
        requirement controllerMass_0997 : Common::MassLimit {
            subject component : Controller_0997;
            attribute :>> limit = 2.0 [kg];
        }
    }

    package Subsystem_0998 {
        part def Sensor_0998 :> Common::Component {
            attribute :>> mass = 0.23 [kg];
            attribute :>> cost = 48.0;
            attribute range : Real = 148.0;
            port data : Common::DataPort;
        }
        part def Controller_0998 :> Common::Component {
            attribute :>> mass = 1.40 [kg];
            attribute :>> cost = 298.0;
            port supply : Common::PowerPort;
            part sensors : Sensor_0998[2];
            action smooth : Common::Process;
            action forward : Common::Process;
            succession first smooth then forward;
            exhibit state lifecycle : Common::Lifecycle;
        }
        requirement controllerMass_0998 : Common::MassLimit {
            subject component : Controller_0998;
            attribute :>> limit = 2.0 [kg];
        }
    }

    package Subsystem_0999 {
        part def Sensor_0999 :> Common::Component {
            attribute :>> mass = 0.24 [kg];
            attribute :>> cost = 49.0;
            attribute range : Real = 149.0;
            port data : Common::DataPort;
        }
        part def Controller_0999 :> Common::Component {
            attribute :>> mass = 1.50 [kg];
            attribute :>> cost = 299.0;
            port supply : Common::PowerPort;
            part sensors : Sensor_0999[2];
            action smooth : Common::Process;
            action forward : Common::Process;
            succession first smooth then forward;
            exhibit state lifecycle : Common::Lifecycle;
        }
        requirement controllerMass_0999 : Common::MassLimit {
            subject component : Controller_0999;
            attribute :>> limit = 2.0 [kg];
        }
    }

    package Subsystem_1000 {
        part def Sensor_1000 :> Common::Component {
            attribute :>> mass = 0.20 [kg];
            attribute :>> cost = 30.0;
            attribute range : Real = 100.0;
            port data : Common::DataPort;
        }
        part def Controller_1000 :> Common::Component {
            attribute :>> mass = 1.60 [kg];
            attribute :>> cost = 200.0;
            port supply : Common::PowerPort;
            part sensors : Sensor_1000[2];
            action smooth : Common::Process;
            action forward : Common::Process;
            succession first smooth then forward;
            exhibit state lifecycle : Common::Lifecycle;
        }
        requirement controllerMass_1000 : Common::MassLimit {
            subject component : Controller_1000;
            attribute :>> limit = 2.0 [kg];
        }
    }

    part def System {
        part controller_0001 : Subsystem_0001::Controller_0001;
        part controller_0002 : Subsystem_0002::Controller_0002;
        part controller_0003 : Subsystem_0003::Controller_0003;
        part controller_0004 : Subsystem_0004::Controller_0004;
        part controller_0005 : Subsystem_0005::Controller_0005;
        part controller_0006 : Subsystem_0006::Controller_0006;
        part controller_0007 : Subsystem_0007::Controller_0007;
        part controller_0008 : Subsystem_0008::Controller_0008;
        part controller_0009 : Subsystem_0009::Controller_0009;
        part controller_0010 : Subsystem_0010::Controller_0010;
        part controller_0011 : Subsystem_0011::Controller_0011;
        part controller_0012 : Subsystem_0012::Controller_0012;
        part controller_0013 : Subsystem_0013::Controller_0013;
        part controller_0014 : Subsystem_0014::Controller_0014;
        part controller_0015 : Subsystem_0015::Controller_0015;
        part controller_0016 : Subsystem_0016::Controller_0016;
        part controller_0017 : Subsystem_0017::Controller_0017;
        part controller_0018 : Subsystem_0018::Controller_0018;
        part controller_0019 : Subsystem_0019::Controller_0019;
        part controller_0020 : Subsystem_0020::Controller_0020;
        part controller_0021 : Subsystem_0021::Controller_0021;
        part controller_0022 : Subsystem_0022::Controller_0022;
        part controller_0023 : Subsystem_0023::Controller_0023;
        part controller_0024 : Subsystem_0024::Controller_0024;
        part controller_0025 : Subsystem_0025::Controller_0025;
        part controller_0026 : Subsystem_0026::Controller_0026;
        part controller_0027 : Subsystem_0027::Controller_0027;
        part controller_0028 : Subsystem_0028::Controller_0028;
        part controller_0029 : Subsystem_0029::Controller_0029;
        part controller_0030 : Subsystem_0030::Controller_0030;
        part controller_0031 : Subsystem_0031::Controller_0031;
        part controller_0032 : Subsystem_0032::Controller_0032;
        part controller_0033 : Subsystem_0033::Controller_0033;
        part controller_0034 : Subsystem_0034::Controller_0034;
        part controller_0035 : Subsystem_0035::Controller_0035;
        part controller_0036 : Subsystem_0036::Controller_0036;
        part controller_0037 : Subsystem_0037::Controller_0037;
        part controller_0038 : Subsystem_0038::Controller_0038;
        part controller_0039 : Subsystem_0039::Controller_0039;
        part controller_0040 : Subsystem_0040::Controller_0040;
        part controller_0041 : Subsystem_0041::Controller_0041;
        part controller_0042 : Subsystem_0042::Controller_0042;
        part controller_0043 : Subsystem_0043::Controller_0043;
        part controller_0044 : Subsystem_0044::Controller_0044;
        part controller_0045 : Subsystem_0045::Controller_0045;
        part controller_0046 : Subsystem_0046::Controller_0046;
        part controller_0047 : Subsystem_0047::Controller_0047;
        part controller_0048 : Subsystem_0048::Controller_0048;
        part controller_0049 : Subsystem_0049::Controller_0049;
        part controller_0050 : Subsystem_0050::Controller_0050;
        part controller_0051 : Subsystem_0051::Controller_0051;
        part controller_0052 : Subsystem_0052::Controller_0052;
        part controller_0053 : Subsystem_0053::Controller_0053;
        part controller_0054 : Subsystem_0054::Controller_0054;
        part controller_0055 : Subsystem_0055::Controller_0055;
        part controller_0056 : Subsystem_0056::Controller_0056;
        part controller_0057 : Subsystem_0057::Controller_0057;
        part controller_0058 : Subsystem_0058::Controller_0058;
        part controller_0059 : Subsystem_0059::Controller_0059;
        part controller_0060 : Subsystem_0060::Controller_0060;
        part controller_0061 : Subsystem_0061::Controller_0061;
        part controller_0062 : Subsystem_0062::Controller_0062;
        part controller_0063 : Subsystem_0063::Controller_0063;
        part controller_0064 : Subsystem_0064::Controller_0064;
        part controller_0065 : Subsystem_0065::Controller_0065;
        part controller_0066 : Subsystem_0066::Controller_0066;
        part controller_0067 : Subsystem_0067::Controller_0067;
        part controller_0068 : Subsystem_0068::Controller_0068;
        part controller_0069 : Subsystem_0069::Controller_0069;
        part controller_0070 : Subsystem_0070::Controller_0070;
        part controller_0071 : Subsystem_0071::Controller_0071;
        part controller_0072 : Subsystem_0072::Controller_0072;
        part controller_0073 : Subsystem_0073::Controller_0073;
        part controller_0074 : Subsystem_0074::Controller_0074;
        part controller_0075 : Subsystem_0075::Controller_0075;
        part controller_0076 : Subsystem_0076::Controller_0076;
        part controller_0077 : Subsystem_0077::Controller_0077;
        part controller_0078 : Subsystem_0078::Controller_0078;
        part controller_0079 : Subsystem_0079::Controller_0079;
        part controller_0080 : Subsystem_0080::Controller_0080;
        part controller_0081 : Subsystem_0081::Controller_0081;
        part controller_0082 : Subsystem_0082::Controller_0082;
        part controller_0083 : Subsystem_0083::Controller_0083;
        part controller_0084 : Subsystem_0084::Controller_0084;
        part controller_0085 : Subsystem_0085::Controller_0085;
        part controller_0086 : Subsystem_0086::Controller_0086;
        part controller_0087 : Subsystem_0087::Controller_0087;
        part controller_0088 : Subsystem_0088::Controller_0088;
        part controller_0089 : Subsystem_0089::Controller_0089;
        part controller_0090 : Subsystem_0090::Controller_0090;
        part controller_0091 : Subsystem_0091::Controller_0091;
        part controller_0092 : Subsystem_0092::Controller_0092;
        part controller_0093 : Subsystem_0093::Controller_0093;
        part controller_0094 : Subsystem_0094::Controller_0094;
        part controller_0095 : Subsystem_0095::Controller_0095;
        part controller_0096 : Subsystem_0096::Controller_0096;
        part controller_0097 : Subsystem_0097::Controller_0097;
        part controller_0098 : Subsystem_0098::Controller_0098;
        part controller_0099 : Subsystem_0099::Controller_0099;
        part controller_0100 : Subsystem_0100::Controller_0100;
        part controller_0101 : Subsystem_0101::Controller_0101;
        part controller_0102 : Subsystem_0102::Controller_0102;
        part controller_0103 : Subsystem_0103::Controller_0103;
        part controller_0104 : Subsystem_0104::Controller_0104;
        part controller_0105 : Subsystem_0105::Controller_0105;
        part controller_0106 : Subsystem_0106::Controller_0106;
        part controller_0107 : Subsystem_0107::Controller_0107;
        part controller_0108 : Subsystem_0108::Controller_0108;
        part controller_0109 : Subsystem_0109::Controller_0109;
        part controller_0110 : Subsystem_0110::Controller_0110;
        part controller_0111 : Subsystem_0111::Controller_0111;
        part controller_0112 : Subsystem_0112::Controller_0112;
        part controller_0113 : Subsystem_0113::Controller_0113;
        part controller_0114 : Subsystem_0114::Controller_0114;
        part controller_0115 : Subsystem_0115::Controller_0115;
        part controller_0116 : Subsystem_0116::Controller_0116;
        part controller_0117 : Subsystem_0117::Controller_0117;
        part controller_0118 : Subsystem_0118::Controller_0118;
        part controller_0119 : Subsystem_0119::Controller_0119;
        part controller_0120 : Subsystem_0120::Controller_0120;
        part controller_0121 : Subsystem_0121::Controller_0121;
        part controller_0122 : Subsystem_0122::Controller_0122;
        part controller_0123 : Subsystem_0123::Controller_0123;
        part controller_0124 : Subsystem_0124::Controller_0124;
        part controller_0125 : Subsystem_0125::Controller_0125;
        part controller_0126 : Subsystem_0126::Controller_0126;
        part controller_0127 : Subsystem_0127::Controller_0127;
        part controller_0128 : Subsystem_0128::Controller_0128;
        part controller_0129 : Subsystem_0129::Controller_0129;
        part controller_0130 : Subsystem_0130::Controller_0130;
        part controller_0131 : Subsystem_0131::Controller_0131;
        part controller_0132 : Subsystem_0132::Controller_0132;
        part controller_0133 : Subsystem_0133::Controller_0133;
        part controller_0134 : Subsystem_0134::Controller_0134;
        part controller_0135 : Subsystem_0135::Controller_0135;
        part controller_0136 : Subsystem_0136::Controller_0136;
        part controller_0137 : Subsystem_0137::Controller_0137;
        part controller_0138 : Subsystem_0138::Controller_0138;
        part controller_0139 : Subsystem_0139::Controller_0139;
        part controller_0140 : Subsystem_0140::Controller_0140;
        part controller_0141 : Subsystem_0141::Controller_0141;
        part controller_0142 : Subsystem_0142::Controller_0142;
        part controller_0143 : Subsystem_0143::Controller_0143;
        part controller_0144 : Subsystem_0144::Controller_0144;
        part controller_0145 : Subsystem_0145::Controller_0145;
        part controller_0146 : Subsystem_0146::Controller_0146;
        part controller_0147 : Subsystem_0147::Controller_0147;
        part controller_0148 : Subsystem_0148::Controller_0148;
        part controller_0149 : Subsystem_0149::Controller_0149;
        part controller_0150 : Subsystem_0150::Controller_0150;
        part controller_0151 : Subsystem_0151::Controller_0151;
        part controller_0152 : Subsystem_0152::Controller_0152;
        part controller_0153 : Subsystem_0153::Controller_0153;
        part controller_0154 : Subsystem_0154::Controller_0154;
        part controller_0155 : Subsystem_0155::Controller_0155;
        part controller_0156 : Subsystem_0156::Controller_0156;
        part controller_0157 : Subsystem_0157::Controller_0157;
        part controller_0158 : Subsystem_0158::Controller_0158;
        part controller_0159 : Subsystem_0159::Controller_0159;
        part controller_0160 : Subsystem_0160::Controller_0160;
        part controller_0161 : Subsystem_0161::Controller_0161;
        part controller_0162 : Subsystem_0162::Controller_0162;
        part controller_0163 : Subsystem_0163::Controller_0163;
        part controller_0164 : Subsystem_0164::Controller_0164;
        part controller_0165 : Subsystem_0165::Controller_0165;
        part controller_0166 : Subsystem_0166::Controller_0166;
        part controller_0167 : Subsystem_0167::Controller_0167;
        part controller_0168 : Subsystem_0168::Controller_0168;
        part controller_0169 : Subsystem_0169::Controller_0169;
        part controller_0170 : Subsystem_0170::Controller_0170;
        part controller_0171 : Subsystem_0171::Controller_0171;
        part controller_0172 : Subsystem_0172::Controller_0172;
        part controller_0173 : Subsystem_0173::Controller_0173;
        part controller_0174 : Subsystem_0174::Controller_0174;
        part controller_0175 : Subsystem_0175::Controller_0175;
        part controller_0176 : Subsystem_0176::Controller_0176;
        part controller_0177 : Subsystem_0177::Controller_0177;
        part controller_0178 : Subsystem_0178::Controller_0178;
        part controller_0179 : Subsystem_0179::Controller_0179;
        part controller_0180 : Subsystem_0180::Controller_0180;
        part controller_0181 : Subsystem_0181::Controller_0181;
        part controller_0182 : Subsystem_0182::Controller_0182;
        part controller_0183 : Subsystem_0183::Controller_0183;
        part controller_0184 : Subsystem_0184::Controller_0184;
        part controller_0185 : Subsystem_0185::Controller_0185;
        part controller_0186 : Subsystem_0186::Controller_0186;
        part controller_0187 : Subsystem_0187::Controller_0187;
        part controller_0188 : Subsystem_0188::Controller_0188;
        part controller_0189 : Subsystem_0189::Controller_0189;
        part controller_0190 : Subsystem_0190::Controller_0190;
        part controller_0191 : Subsystem_0191::Controller_0191;
        part controller_0192 : Subsystem_0192::Controller_0192;
        part controller_0193 : Subsystem_0193::Controller_0193;
        part controller_0194 : Subsystem_0194::Controller_0194;
        part controller_0195 : Subsystem_0195::Controller_0195;
        part controller_0196 : Subsystem_0196::Controller_0196;
        part controller_0197 : Subsystem_0197::Controller_0197;
        part controller_0198 : Subsystem_0198::Controller_0198;
        part controller_0199 : Subsystem_0199::Controller_0199;
        part controller_0200 : Subsystem_0200::Controller_0200;
        part controller_0201 : Subsystem_0201::Controller_0201;
        part controller_0202 : Subsystem_0202::Controller_0202;
        part controller_0203 : Subsystem_0203::Controller_0203;
        part controller_0204 : Subsystem_0204::Controller_0204;
        part controller_0205 : Subsystem_0205::Controller_0205;
        part controller_0206 : Subsystem_0206::Controller_0206;
        part controller_0207 : Subsystem_0207::Controller_0207;
        part controller_0208 : Subsystem_0208::Controller_0208;
        part controller_0209 : Subsystem_0209::Controller_0209;
        part controller_0210 : Subsystem_0210::Controller_0210;
        part controller_0211 : Subsystem_0211::Controller_0211;
        part controller_0212 : Subsystem_0212::Controller_0212;
        part controller_0213 : Subsystem_0213::Controller_0213;
        part controller_0214 : Subsystem_0214::Controller_0214;
        part controller_0215 : Subsystem_0215::Controller_0215;
        part controller_0216 : Subsystem_0216::Controller_0216;
        part controller_0217 : Subsystem_0217::Controller_0217;
        part controller_0218 : Subsystem_0218::Controller_0218;
        part controller_0219 : Subsystem_0219::Controller_0219;
        part controller_0220 : Subsystem_0220::Controller_0220;
        part controller_0221 : Subsystem_0221::Controller_0221;
        part controller_0222 : Subsystem_0222::Controller_0222;
        part controller_0223 : Subsystem_0223::Controller_0223;
        part controller_0224 : Subsystem_0224::Controller_0224;
        part controller_0225 : Subsystem_0225::Controller_0225;
        part controller_0226 : Subsystem_0226::Controller_0226;
        part controller_0227 : Subsystem_0227::Controller_0227;
        part controller_0228 : Subsystem_0228::Controller_0228;
        part controller_0229 : Subsystem_0229::Controller_0229;
        part controller_0230 : Subsystem_0230::Controller_0230;
        part controller_0231 : Subsystem_0231::Controller_0231;
        part controller_0232 : Subsystem_0232::Controller_0232;
        part controller_0233 : Subsystem_0233::Controller_0233;
        part controller_0234 : Subsystem_0234::Controller_0234;
        part controller_0235 : Subsystem_0235::Controller_0235;
        part controller_0236 : Subsystem_0236::Controller_0236;
        part controller_0237 : Subsystem_0237::Controller_0237;
        part controller_0238 : Subsystem_0238::Controller_0238;
        part controller_0239 : Subsystem_0239::Controller_0239;
        part controller_0240 : Subsystem_0240::Controller_0240;
        part controller_0241 : Subsystem_0241::Controller_0241;
        part controller_0242 : Subsystem_0242::Controller_0242;
        part controller_0243 : Subsystem_0243::Controller_0243;
        part controller_0244 : Subsystem_0244::Controller_0244;
        part controller_0245 : Subsystem_0245::Controller_0245;
        part controller_0246 : Subsystem_0246::Controller_0246;
        part controller_0247 : Subsystem_0247::Controller_0247;
        part controller_0248 : Subsystem_0248::Controller_0248;
        part controller_0249 : Subsystem_0249::Controller_0249;
        part controller_0250 : Subsystem_0250::Controller_0250;
        part controller_0251 : Subsystem_0251::Controller_0251;
        part controller_0252 : Subsystem_0252::Controller_0252;
        part controller_0253 : Subsystem_0253::Controller_0253;
        part controller_0254 : Subsystem_0254::Controller_0254;
        part controller_0255 : Subsystem_0255::Controller_0255;
        part controller_0256 : Subsystem_0256::Controller_0256;
        part controller_0257 : Subsystem_0257::Controller_0257;
        part controller_0258 : Subsystem_0258::Controller_0258;
        part controller_0259 : Subsystem_0259::Controller_0259;
        part controller_0260 : Subsystem_0260::Controller_0260;
        part controller_0261 : Subsystem_0261::Controller_0261;
        part controller_0262 : Subsystem_0262::Controller_0262;
        part controller_0263 : Subsystem_0263::Controller_0263;
        part controller_0264 : Subsystem_0264::Controller_0264;
        part controller_0265 : Subsystem_0265::Controller_0265;
        part controller_0266 : Subsystem_0266::Controller_0266;
        part controller_0267 : Subsystem_0267::Controller_0267;
        part controller_0268 : Subsystem_0268::Controller_0268;
        part controller_0269 : Subsystem_0269::Controller_0269;
        part controller_0270 : Subsystem_0270::Controller_0270;
        part controller_0271 : Subsystem_0271::Controller_0271;
        part controller_0272 : Subsystem_0272::Controller_0272;
        part controller_0273 : Subsystem_0273::Controller_0273;
        part controller_0274 : Subsystem_0274::Controller_0274;
        part controller_0275 : Subsystem_0275::Controller_0275;
        part controller_0276 : Subsystem_0276::Controller_0276;
        part controller_0277 : Subsystem_0277::Controller_0277;
        part controller_0278 : Subsystem_0278::Controller_0278;
        part controller_0279 : Subsystem_0279::Controller_0279;
        part controller_0280 : Subsystem_0280::Controller_0280;
        part controller_0281 : Subsystem_0281::Controller_0281;
        part controller_0282 : Subsystem_0282::Controller_0282;
        part controller_0283 : Subsystem_0283::Controller_0283;
        part controller_0284 : Subsystem_0284::Controller_0284;
        part controller_0285 : Subsystem_0285::Controller_0285;
        part controller_0286 : Subsystem_0286::Controller_0286;
        part controller_0287 : Subsystem_0287::Controller_0287;
        part controller_0288 : Subsystem_0288::Controller_0288;
        part controller_0289 : Subsystem_0289::Controller_0289;
        part controller_0290 : Subsystem_0290::Controller_0290;
        part controller_0291 : Subsystem_0291::Controller_0291;
        part controller_0292 : Subsystem_0292::Controller_0292;
        part controller_0293 : Subsystem_0293::Controller_0293;
        part controller_0294 : Subsystem_0294::Controller_0294;
        part controller_0295 : Subsystem_0295::Controller_0295;
        part controller_0296 : Subsystem_0296::Controller_0296;
        part controller_0297 : Subsystem_0297::Controller_0297;
        part controller_0298 : Subsystem_0298::Controller_0298;
        part controller_0299 : Subsystem_0299::Controller_0299;
        part controller_0300 : Subsystem_0300::Controller_0300;
        part controller_0301 : Subsystem_0301::Controller_0301;
        part controller_0302 : Subsystem_0302::Controller_0302;
        part controller_0303 : Subsystem_0303::Controller_0303;
        part controller_0304 : Subsystem_0304::Controller_0304;
        part controller_0305 : Subsystem_0305::Controller_0305;
        part controller_0306 : Subsystem_0306::Controller_0306;
        part controller_0307 : Subsystem_0307::Controller_0307;
        part controller_0308 : Subsystem_0308::Controller_0308;
        part controller_0309 : Subsystem_0309::Controller_0309;
        part controller_0310 : Subsystem_0310::Controller_0310;
        part controller_0311 : Subsystem_0311::Controller_0311;
        part controller_0312 : Subsystem_0312::Controller_0312;
        part controller_0313 : Subsystem_0313::Controller_0313;
        part controller_0314 : Subsystem_0314::Controller_0314;
        part controller_0315 : Subsystem_0315::Controller_0315;
        part controller_0316 : Subsystem_0316::Controller_0316;
        part controller_0317 : Subsystem_0317::Controller_0317;
        part controller_0318 : Subsystem_0318::Controller_0318;
        part controller_0319 : Subsystem_0319::Controller_0319;
        part controller_0320 : Subsystem_0320::Controller_0320;
        part controller_0321 : Subsystem_0321::Controller_0321;
        part controller_0322 : Subsystem_0322::Controller_0322;
        part controller_0323 : Subsystem_0323::Controller_0323;
        part controller_0324 : Subsystem_0324::Controller_0324;
        part controller_0325 : Subsystem_0325::Controller_0325;
        part controller_0326 : Subsystem_0326::Controller_0326;
        part controller_0327 : Subsystem_0327::Controller_0327;
        part controller_0328 : Subsystem_0328::Controller_0328;
        part controller_0329 : Subsystem_0329::Controller_0329;
        part controller_0330 : Subsystem_0330::Controller_0330;
        part controller_0331 : Subsystem_0331::Controller_0331;
        part controller_0332 : Subsystem_0332::Controller_0332;
        part controller_0333 : Subsystem_0333::Controller_0333;
        part controller_0334 : Subsystem_0334::Controller_0334;
        part controller_0335 : Subsystem_0335::Controller_0335;
        part controller_0336 : Subsystem_0336::Controller_0336;
        part controller_0337 : Subsystem_0337::Controller_0337;
        part controller_0338 : Subsystem_0338::Controller_0338;
        part controller_0339 : Subsystem_0339::Controller_0339;
        part controller_0340 : Subsystem_0340::Controller_0340;
        part controller_0341 : Subsystem_0341::Controller_0341;
        part controller_0342 : Subsystem_0342::Controller_0342;
        part controller_0343 : Subsystem_0343::Controller_0343;
        part controller_0344 : Subsystem_0344::Controller_0344;
        part controller_0345 : Subsystem_0345::Controller_0345;
        part controller_0346 : Subsystem_0346::Controller_0346;
        part controller_0347 : Subsystem_0347::Controller_0347;
        part controller_0348 : Subsystem_0348::Controller_0348;
        part controller_0349 : Subsystem_0349::Controller_0349;
        part controller_0350 : Subsystem_0350::Controller_0350;
        part controller_0351 : Subsystem_0351::Controller_0351;
        part controller_0352 : Subsystem_0352::Controller_0352;
        part controller_0353 : Subsystem_0353::Controller_0353;
        part controller_0354 : Subsystem_0354::Controller_0354;
        part controller_0355 : Subsystem_0355::Controller_0355;
        part controller_0356 : Subsystem_0356::Controller_0356;
        part controller_0357 : Subsystem_0357::Controller_0357;
        part controller_0358 : Subsystem_0358::Controller_0358;
        part controller_0359 : Subsystem_0359::Controller_0359;
        part controller_0360 : Subsystem_0360::Controller_0360;
        part controller_0361 : Subsystem_0361::Controller_0361;
        part controller_0362 : Subsystem_0362::Controller_0362;
        part controller_0363 : Subsystem_0363::Controller_0363;
        part controller_0364 : Subsystem_0364::Controller_0364;
        part controller_0365 : Subsystem_0365::Controller_0365;
        part controller_0366 : Subsystem_0366::Controller_0366;
        part controller_0367 : Subsystem_0367::Controller_0367;
        part controller_0368 : Subsystem_0368::Controller_0368;
        part controller_0369 : Subsystem_0369::Controller_0369;
        part controller_0370 : Subsystem_0370::Controller_0370;
        part controller_0371 : Subsystem_0371::Controller_0371;
        part controller_0372 : Subsystem_0372::Controller_0372;
        part controller_0373 : Subsystem_0373::Controller_0373;
        part controller_0374 : Subsystem_0374::Controller_0374;
        part controller_0375 : Subsystem_0375::Controller_0375;
        part controller_0376 : Subsystem_0376::Controller_0376;
        part controller_0377 : Subsystem_0377::Controller_0377;
        part controller_0378 : Subsystem_0378::Controller_0378;
        part controller_0379 : Subsystem_0379::Controller_0379;
        part controller_0380 : Subsystem_0380::Controller_0380;
        part controller_0381 : Subsystem_0381::Controller_0381;
        part controller_0382 : Subsystem_0382::Controller_0382;
        part controller_0383 : Subsystem_0383::Controller_0383;
        part controller_0384 : Subsystem_0384::Controller_0384;
        part controller_0385 : Subsystem_0385::Controller_0385;
        part controller_0386 : Subsystem_0386::Controller_0386;
        part controller_0387 : Subsystem_0387::Controller_0387;
        part controller_0388 : Subsystem_0388::Controller_0388;
        part controller_0389 : Subsystem_0389::Controller_0389;
        part controller_0390 : Subsystem_0390::Controller_0390;
        part controller_0391 : Subsystem_0391::Controller_0391;
        part controller_0392 : Subsystem_0392::Controller_0392;
        part controller_0393 : Subsystem_0393::Controller_0393;
        part controller_0394 : Subsystem_0394::Controller_0394;
        part controller_0395 : Subsystem_0395::Controller_0395;
        part controller_0396 : Subsystem_0396::Controller_0396;
        part controller_0397 : Subsystem_0397::Controller_0397;
        part controller_0398 : Subsystem_0398::Controller_0398;
        part controller_0399 : Subsystem_0399::Controller_0399;
        part controller_0400 : Subsystem_0400::Controller_0400;
        part controller_0401 : Subsystem_0401::Controller_0401;
        part controller_0402 : Subsystem_0402::Controller_0402;
        part controller_0403 : Subsystem_0403::Controller_0403;
        part controller_0404 : Subsystem_0404::Controller_0404;
        part controller_0405 : Subsystem_0405::Controller_0405;
        part controller_0406 : Subsystem_0406::Controller_0406;
        part controller_0407 : Subsystem_0407::Controller_0407;
        part controller_0408 : Subsystem_0408::Controller_0408;
        part controller_0409 : Subsystem_0409::Controller_0409;
        part controller_0410 : Subsystem_0410::Controller_0410;
        part controller_0411 : Subsystem_0411::Controller_0411;
        part controller_0412 : Subsystem_0412::Controller_0412;
        part controller_0413 : Subsystem_0413::Controller_0413;
        part controller_0414 : Subsystem_0414::Controller_0414;
        part controller_0415 : Subsystem_0415::Controller_0415;
        part controller_0416 : Subsystem_0416::Controller_0416;
        part controller_0417 : Subsystem_0417::Controller_0417;
        part controller_0418 : Subsystem_0418::Controller_0418;
        part controller_0419 : Subsystem_0419::Controller_0419;
        part controller_0420 : Subsystem_0420::Controller_0420;
        part controller_0421 : Subsystem_0421::Controller_0421;
        part controller_0422 : Subsystem_0422::Controller_0422;
        part controller_0423 : Subsystem_0423::Controller_0423;
        part controller_0424 : Subsystem_0424::Controller_0424;
        part controller_0425 : Subsystem_0425::Controller_0425;
        part controller_0426 : Subsystem_0426::Controller_0426;
        part controller_0427 : Subsystem_0427::Controller_0427;
        part controller_0428 : Subsystem_0428::Controller_0428;
        part controller_0429 : Subsystem_0429::Controller_0429;
        part controller_0430 : Subsystem_0430::Controller_0430;
        part controller_0431 : Subsystem_0431::Controller_0431;
        part controller_0432 : Subsystem_0432::Controller_0432;
        part controller_0433 : Subsystem_0433::Controller_0433;
        part controller_0434 : Subsystem_0434::Controller_0434;
        part controller_0435 : Subsystem_0435::Controller_0435;
        part controller_0436 : Subsystem_0436::Controller_0436;
        part controller_0437 : Subsystem_0437::Controller_0437;
        part controller_0438 : Subsystem_0438::Controller_0438;
        part controller_0439 : Subsystem_0439::Controller_0439;
        part controller_0440 : Subsystem_0440::Controller_0440;
        part controller_0441 : Subsystem_0441::Controller_0441;
        part controller_0442 : Subsystem_0442::Controller_0442;
        part controller_0443 : Subsystem_0443::Controller_0443;
        part controller_0444 : Subsystem_0444::Controller_0444;
        part controller_0445 : Subsystem_0445::Controller_0445;
        part controller_0446 : Subsystem_0446::Controller_0446;
        part controller_0447 : Subsystem_0447::Controller_0447;
        part controller_0448 : Subsystem_0448::Controller_0448;
        part controller_0449 : Subsystem_0449::Controller_0449;
        part controller_0450 : Subsystem_0450::Controller_0450;
        part controller_0451 : Subsystem_0451::Controller_0451;
        part controller_0452 : Subsystem_0452::Controller_0452;
        part controller_0453 : Subsystem_0453::Controller_0453;
        part controller_0454 : Subsystem_0454::Controller_0454;
        part controller_0455 : Subsystem_0455::Controller_0455;
        part controller_0456 : Subsystem_0456::Controller_0456;
        part controller_0457 : Subsystem_0457::Controller_0457;
        part controller_0458 : Subsystem_0458::Controller_0458;
        part controller_0459 : Subsystem_0459::Controller_0459;
        part controller_0460 : Subsystem_0460::Controller_0460;
        part controller_0461 : Subsystem_0461::Controller_0461;
        part controller_0462 : Subsystem_0462::Controller_0462;
        part controller_0463 : Subsystem_0463::Controller_0463;
        part controller_0464 : Subsystem_0464::Controller_0464;
        part controller_0465 : Subsystem_0465::Controller_0465;
        part controller_0466 : Subsystem_0466::Controller_0466;
        part controller_0467 : Subsystem_0467::Controller_0467;
        part controller_0468 : Subsystem_0468::Controller_0468;
        part controller_0469 : Subsystem_0469::Controller_0469;
        part controller_0470 : Subsystem_0470::Controller_0470;
        part controller_0471 : Subsystem_0471::Controller_0471;
        part controller_0472 : Subsystem_0472::Controller_0472;
        part controller_0473 : Subsystem_0473::Controller_0473;
        part controller_0474 : Subsystem_0474::Controller_0474;
        part controller_0475 : Subsystem_0475::Controller_0475;
        part controller_0476 : Subsystem_0476::Controller_0476;
        part controller_0477 : Subsystem_0477::Controller_0477;
        part controller_0478 : Subsystem_0478::Controller_0478;
        part controller_0479 : Subsystem_0479::Controller_0479;
        part controller_0480 : Subsystem_0480::Controller_0480;
        part controller_0481 : Subsystem_0481::Controller_0481;
        part controller_0482 : Subsystem_0482::Controller_0482;
        part controller_0483 : Subsystem_0483::Controller_0483;
        part controller_0484 : Subsystem_0484::Controller_0484;
        part controller_0485 : Subsystem_0485::Controller_0485;
        part controller_0486 : Subsystem_0486::Controller_0486;
        part controller_0487 : Subsystem_0487::Controller_0487;
        part controller_0488 : Subsystem_0488::Controller_0488;
        part controller_0489 : Subsystem_0489::Controller_0489;
        part controller_0490 : Subsystem_0490::Controller_0490;
        part controller_0491 : Subsystem_0491::Controller_0491;
        part controller_0492 : Subsystem_0492::Controller_0492;
        part controller_0493 : Subsystem_0493::Controller_0493;
        part controller_0494 : Subsystem_0494::Controller_0494;
        part controller_0495 : Subsystem_0495::Controller_0495;
        part controller_0496 : Subsystem_0496::Controller_0496;
        part controller_0497 : Subsystem_0497::Controller_0497;
        part controller_0498 : Subsystem_0498::Controller_0498;
        part controller_0499 : Subsystem_0499::Controller_0499;
        part controller_0500 : Subsystem_0500::Controller_0500;
        part controller_0501 : Subsystem_0501::Controller_0501;
        part controller_0502 : Subsystem_0502::Controller_0502;
        part controller_0503 : Subsystem_0503::Controller_0503;
        part controller_0504 : Subsystem_0504::Controller_0504;
        part controller_0505 : Subsystem_0505::Controller_0505;
        part controller_0506 : Subsystem_0506::Controller_0506;
        part controller_0507 : Subsystem_0507::Controller_0507;
        part controller_0508 : Subsystem_0508::Controller_0508;
        part controller_0509 : Subsystem_0509::Controller_0509;
        part controller_0510 : Subsystem_0510::Controller_0510;
        part controller_0511 : Subsystem_0511::Controller_0511;
        part controller_0512 : Subsystem_0512::Controller_0512;
        part controller_0513 : Subsystem_0513::Controller_0513;
        part controller_0514 : Subsystem_0514::Controller_0514;
        part controller_0515 : Subsystem_0515::Controller_0515;
        part controller_0516 : Subsystem_0516::Controller_0516;
        part controller_0517 : Subsystem_0517::Controller_0517;
        part controller_0518 : Subsystem_0518::Controller_0518;
        part controller_0519 : Subsystem_0519::Controller_0519;
        part controller_0520 : Subsystem_0520::Controller_0520;
        part controller_0521 : Subsystem_0521::Controller_0521;
        part controller_0522 : Subsystem_0522::Controller_0522;
        part controller_0523 : Subsystem_0523::Controller_0523;
        part controller_0524 : Subsystem_0524::Controller_0524;
        part controller_0525 : Subsystem_0525::Controller_0525;
        part controller_0526 : Subsystem_0526::Controller_0526;
        part controller_0527 : Subsystem_0527::Controller_0527;
        part controller_0528 : Subsystem_0528::Controller_0528;
        part controller_0529 : Subsystem_0529::Controller_0529;
        part controller_0530 : Subsystem_0530::Controller_0530;
        part controller_0531 : Subsystem_0531::Controller_0531;
        part controller_0532 : Subsystem_0532::Controller_0532;
        part controller_0533 : Subsystem_0533::Controller_0533;
        part controller_0534 : Subsystem_0534::Controller_0534;
        part controller_0535 : Subsystem_0535::Controller_0535;
        part controller_0536 : Subsystem_0536::Controller_0536;
        part controller_0537 : Subsystem_0537::Controller_0537;
        part controller_0538 : Subsystem_0538::Controller_0538;
        part controller_0539 : Subsystem_0539::Controller_0539;
        part controller_0540 : Subsystem_0540::Controller_0540;
        part controller_0541 : Subsystem_0541::Controller_0541;
        part controller_0542 : Subsystem_0542::Controller_0542;
        part controller_0543 : Subsystem_0543::Controller_0543;
        part controller_0544 : Subsystem_0544::Controller_0544;
        part controller_0545 : Subsystem_0545::Controller_0545;
        part controller_0546 : Subsystem_0546::Controller_0546;
        part controller_0547 : Subsystem_0547::Controller_0547;
        part controller_0548 : Subsystem_0548::Controller_0548;
        part controller_0549 : Subsystem_0549::Controller_0549;
        part controller_0550 : Subsystem_0550::Controller_0550;
        part controller_0551 : Subsystem_0551::Controller_0551;
        part controller_0552 : Subsystem_0552::Controller_0552;
        part controller_0553 : Subsystem_0553::Controller_0553;
        part controller_0554 : Subsystem_0554::Controller_0554;
        part controller_0555 : Subsystem_0555::Controller_0555;
        part controller_0556 : Subsystem_0556::Controller_0556;
        part controller_0557 : Subsystem_0557::Controller_0557;
        part controller_0558 : Subsystem_0558::Controller_0558;
        part controller_0559 : Subsystem_0559::Controller_0559;
        part controller_0560 : Subsystem_0560::Controller_0560;
        part controller_0561 : Subsystem_0561::Controller_0561;
        part controller_0562 : Subsystem_0562::Controller_0562;
        part controller_0563 : Subsystem_0563::Controller_0563;
        part controller_0564 : Subsystem_0564::Controller_0564;
        part controller_0565 : Subsystem_0565::Controller_0565;
        part controller_0566 : Subsystem_0566::Controller_0566;
        part controller_0567 : Subsystem_0567::Controller_0567;
        part controller_0568 : Subsystem_0568::Controller_0568;
        part controller_0569 : Subsystem_0569::Controller_0569;
        part controller_0570 : Subsystem_0570::Controller_0570;
        part controller_0571 : Subsystem_0571::Controller_0571;
        part controller_0572 : Subsystem_0572::Controller_0572;
        part controller_0573 : Subsystem_0573::Controller_0573;
        part controller_0574 : Subsystem_0574::Controller_0574;
        part controller_0575 : Subsystem_0575::Controller_0575;
        part controller_0576 : Subsystem_0576::Controller_0576;
        part controller_0577 : Subsystem_0577::Controller_0577;
        part controller_0578 : Subsystem_0578::Controller_0578;
        part controller_0579 : Subsystem_0579::Controller_0579;
        part controller_0580 : Subsystem_0580::Controller_0580;
        part controller_0581 : Subsystem_0581::Controller_0581;
        part controller_0582 : Subsystem_0582::Controller_0582;
        part controller_0583 : Subsystem_0583::Controller_0583;
        part controller_0584 : Subsystem_0584::Controller_0584;
        part controller_0585 : Subsystem_0585::Controller_0585;
        part controller_0586 : Subsystem_0586::Controller_0586;
        part controller_0587 : Subsystem_0587::Controller_0587;
        part controller_0588 : Subsystem_0588::Controller_0588;
        part controller_0589 : Subsystem_0589::Controller_0589;
        part controller_0590 : Subsystem_0590::Controller_0590;
        part controller_0591 : Subsystem_0591::Controller_0591;
        part controller_0592 : Subsystem_0592::Controller_0592;
        part controller_0593 : Subsystem_0593::Controller_0593;
        part controller_0594 : Subsystem_0594::Controller_0594;
        part controller_0595 : Subsystem_0595::Controller_0595;
        part controller_0596 : Subsystem_0596::Controller_0596;
        part controller_0597 : Subsystem_0597::Controller_0597;
        part controller_0598 : Subsystem_0598::Controller_0598;
        part controller_0599 : Subsystem_0599::Controller_0599;
        part controller_0600 : Subsystem_0600::Controller_0600;
        part controller_0601 : Subsystem_0601::Controller_0601;
        part controller_0602 : Subsystem_0602::Controller_0602;
        part controller_0603 : Subsystem_0603::Controller_0603;
        part controller_0604 : Subsystem_0604::Controller_0604;
        part controller_0605 : Subsystem_0605::Controller_0605;
        part controller_0606 : Subsystem_0606::Controller_0606;
        part controller_0607 : Subsystem_0607::Controller_0607;
        part controller_0608 : Subsystem_0608::Controller_0608;
        part controller_0609 : Subsystem_0609::Controller_0609;
        part controller_0610 : Subsystem_0610::Controller_0610;
        part controller_0611 : Subsystem_0611::Controller_0611;
        part controller_0612 : Subsystem_0612::Controller_0612;
        part controller_0613 : Subsystem_0613::Controller_0613;
        part controller_0614 : Subsystem_0614::Controller_0614;
        part controller_0615 : Subsystem_0615::Controller_0615;
        part controller_0616 : Subsystem_0616::Controller_0616;
        part controller_0617 : Subsystem_0617::Controller_0617;
        part controller_0618 : Subsystem_0618::Controller_0618;
        part controller_0619 : Subsystem_0619::Controller_0619;
        part controller_0620 : Subsystem_0620::Controller_0620;
        part controller_0621 : Subsystem_0621::Controller_0621;
        part controller_0622 : Subsystem_0622::Controller_0622;
        part controller_0623 : Subsystem_0623::Controller_0623;
        part controller_0624 : Subsystem_0624::Controller_0624;
        part controller_0625 : Subsystem_0625::Controller_0625;
        part controller_0626 : Subsystem_0626::Controller_0626;
        part controller_0627 : Subsystem_0627::Controller_0627;
        part controller_0628 : Subsystem_0628::Controller_0628;
        part controller_0629 : Subsystem_0629::Controller_0629;
        part controller_0630 : Subsystem_0630::Controller_0630;
        part controller_0631 : Subsystem_0631::Controller_0631;
        part controller_0632 : Subsystem_0632::Controller_0632;
        part controller_0633 : Subsystem_0633::Controller_0633;
        part controller_0634 : Subsystem_0634::Controller_0634;
        part controller_0635 : Subsystem_0635::Controller_0635;
        part controller_0636 : Subsystem_0636::Controller_0636;
        part controller_0637 : Subsystem_0637::Controller_0637;
        part controller_0638 : Subsystem_0638::Controller_0638;
        part controller_0639 : Subsystem_0639::Controller_0639;
        part controller_0640 : Subsystem_0640::Controller_0640;
        part controller_0641 : Subsystem_0641::Controller_0641;
        part controller_0642 : Subsystem_0642::Controller_0642;
        part controller_0643 : Subsystem_0643::Controller_0643;
        part controller_0644 : Subsystem_0644::Controller_0644;
        part controller_0645 : Subsystem_0645::Controller_0645;
        part controller_0646 : Subsystem_0646::Controller_0646;
        part controller_0647 : Subsystem_0647::Controller_0647;
        part controller_0648 : Subsystem_0648::Controller_0648;
        part controller_0649 : Subsystem_0649::Controller_0649;
        part controller_0650 : Subsystem_0650::Controller_0650;
        part controller_0651 : Subsystem_0651::Controller_0651;
        part controller_0652 : Subsystem_0652::Controller_0652;
        part controller_0653 : Subsystem_0653::Controller_0653;
        part controller_0654 : Subsystem_0654::Controller_0654;
        part controller_0655 : Subsystem_0655::Controller_0655;
        part controller_0656 : Subsystem_0656::Controller_0656;
        part controller_0657 : Subsystem_0657::Controller_0657;
        part controller_0658 : Subsystem_0658::Controller_0658;
        part controller_0659 : Subsystem_0659::Controller_0659;
        part controller_0660 : Subsystem_0660::Controller_0660;
        part controller_0661 : Subsystem_0661::Controller_0661;
        part controller_0662 : Subsystem_0662::Controller_0662;
        part controller_0663 : Subsystem_0663::Controller_0663;
        part controller_0664 : Subsystem_0664::Controller_0664;
        part controller_0665 : Subsystem_0665::Controller_0665;
        part controller_0666 : Subsystem_0666::Controller_0666;
        part controller_0667 : Subsystem_0667::Controller_0667;
        part controller_0668 : Subsystem_0668::Controller_0668;
        part controller_0669 : Subsystem_0669::Controller_0669;
        part controller_0670 : Subsystem_0670::Controller_0670;
        part controller_0671 : Subsystem_0671::Controller_0671;
        part controller_0672 : Subsystem_0672::Controller_0672;
        part controller_0673 : Subsystem_0673::Controller_0673;
        part controller_0674 : Subsystem_0674::Controller_0674;
        part controller_0675 : Subsystem_0675::Controller_0675;
        part controller_0676 : Subsystem_0676::Controller_0676;
        part controller_0677 : Subsystem_0677::Controller_0677;
        part controller_0678 : Subsystem_0678::Controller_0678;
        part controller_0679 : Subsystem_0679::Controller_0679;
        part controller_0680 : Subsystem_0680::Controller_0680;
        part controller_0681 : Subsystem_0681::Controller_0681;
        part controller_0682 : Subsystem_0682::Controller_0682;
        part controller_0683 : Subsystem_0683::Controller_0683;
        part controller_0684 : Subsystem_0684::Controller_0684;
        part controller_0685 : Subsystem_0685::Controller_0685;
        part controller_0686 : Subsystem_0686::Controller_0686;
        part controller_0687 : Subsystem_0687::Controller_0687;
        part controller_0688 : Subsystem_0688::Controller_0688;
        part controller_0689 : Subsystem_0689::Controller_0689;
        part controller_0690 : Subsystem_0690::Controller_0690;
        part controller_0691 : Subsystem_0691::Controller_0691;
        part controller_0692 : Subsystem_0692::Controller_0692;
        part controller_0693 : Subsystem_0693::Controller_0693;
        part controller_0694 : Subsystem_0694::Controller_0694;
        part controller_0695 : Subsystem_0695::Controller_0695;
        part controller_0696 : Subsystem_0696::Controller_0696;
        part controller_0697 : Subsystem_0697::Controller_0697;
        part controller_0698 : Subsystem_0698::Controller_0698;
        part controller_0699 : Subsystem_0699::Controller_0699;
        part controller_0700 : Subsystem_0700::Controller_0700;
        part controller_0701 : Subsystem_0701::Controller_0701;
        part controller_0702 : Subsystem_0702::Controller_0702;
        part controller_0703 : Subsystem_0703::Controller_0703;
        part controller_0704 : Subsystem_0704::Controller_0704;
        part controller_0705 : Subsystem_0705::Controller_0705;
        part controller_0706 : Subsystem_0706::Controller_0706;
        part controller_0707 : Subsystem_0707::Controller_0707;
        part controller_0708 : Subsystem_0708::Controller_0708;
        part controller_0709 : Subsystem_0709::Controller_0709;
        part controller_0710 : Subsystem_0710::Controller_0710;
        part controller_0711 : Subsystem_0711::Controller_0711;
        part controller_0712 : Subsystem_0712::Controller_0712;
        part controller_0713 : Subsystem_0713::Controller_0713;
        part controller_0714 : Subsystem_0714::Controller_0714;
        part controller_0715 : Subsystem_0715::Controller_0715;
        part controller_0716 : Subsystem_0716::Controller_0716;
        part controller_0717 : Subsystem_0717::Controller_0717;
        part controller_0718 : Subsystem_0718::Controller_0718;
        part controller_0719 : Subsystem_0719::Controller_0719;
        part controller_0720 : Subsystem_0720::Controller_0720;
        part controller_0721 : Subsystem_0721::Controller_0721;
        part controller_0722 : Subsystem_0722::Controller_0722;
        part controller_0723 : Subsystem_0723::Controller_0723;
        part controller_0724 : Subsystem_0724::Controller_0724;
        part controller_0725 : Subsystem_0725::Controller_0725;
        part controller_0726 : Subsystem_0726::Controller_0726;
        part controller_0727 : Subsystem_0727::Controller_0727;
        part controller_0728 : Subsystem_0728::Controller_0728;
        part controller_0729 : Subsystem_0729::Controller_0729;
        part controller_0730 : Subsystem_0730::Controller_0730;
        part controller_0731 : Subsystem_0731::Controller_0731;
        part controller_0732 : Subsystem_0732::Controller_0732;
        part controller_0733 : Subsystem_0733::Controller_0733;
        part controller_0734 : Subsystem_0734::Controller_0734;
        part controller_0735 : Subsystem_0735::Controller_0735;
        part controller_0736 : Subsystem_0736::Controller_0736;
        part controller_0737 : Subsystem_0737::Controller_0737;
        part controller_0738 : Subsystem_0738::Controller_0738;
        part controller_0739 : Subsystem_0739::Controller_0739;
        part controller_0740 : Subsystem_0740::Controller_0740;
        part controller_0741 : Subsystem_0741::Controller_0741;
        part controller_0742 : Subsystem_0742::Controller_0742;
        part controller_0743 : Subsystem_0743::Controller_0743;
        part controller_0744 : Subsystem_0744::Controller_0744;
        part controller_0745 : Subsystem_0745::Controller_0745;
        part controller_0746 : Subsystem_0746::Controller_0746;
        part controller_0747 : Subsystem_0747::Controller_0747;
        part controller_0748 : Subsystem_0748::Controller_0748;
        part controller_0749 : Subsystem_0749::Controller_0749;
        part controller_0750 : Subsystem_0750::Controller_0750;
        part controller_0751 : Subsystem_0751::Controller_0751;
        part controller_0752 : Subsystem_0752::Controller_0752;
        part controller_0753 : Subsystem_0753::Controller_0753;
        part controller_0754 : Subsystem_0754::Controller_0754;
        part controller_0755 : Subsystem_0755::Controller_0755;
        part controller_0756 : Subsystem_0756::Controller_0756;
        part controller_0757 : Subsystem_0757::Controller_0757;
        part controller_0758 : Subsystem_0758::Controller_0758;
        part controller_0759 : Subsystem_0759::Controller_0759;
        part controller_0760 : Subsystem_0760::Controller_0760;
        part controller_0761 : Subsystem_0761::Controller_0761;
        part controller_0762 : Subsystem_0762::Controller_0762;
        part controller_0763 : Subsystem_0763::Controller_0763;
        part controller_0764 : Subsystem_0764::Controller_0764;
        part controller_0765 : Subsystem_0765::Controller_0765;
        part controller_0766 : Subsystem_0766::Controller_0766;
        part controller_0767 : Subsystem_0767::Controller_0767;
        part controller_0768 : Subsystem_0768::Controller_0768;
        part controller_0769 : Subsystem_0769::Controller_0769;
        part controller_0770 : Subsystem_0770::Controller_0770;
        part controller_0771 : Subsystem_0771::Controller_0771;
        part controller_0772 : Subsystem_0772::Controller_0772;
        part controller_0773 : Subsystem_0773::Controller_0773;
        part controller_0774 : Subsystem_0774::Controller_0774;
        part controller_0775 : Subsystem_0775::Controller_0775;
        part controller_0776 : Subsystem_0776::Controller_0776;
        part controller_0777 : Subsystem_0777::Controller_0777;
        part controller_0778 : Subsystem_0778::Controller_0778;
        part controller_0779 : Subsystem_0779::Controller_0779;
        part controller_0780 : Subsystem_0780::Controller_0780;
        part controller_0781 : Subsystem_0781::Controller_0781;
        part controller_0782 : Subsystem_0782::Controller_0782;
        part controller_0783 : Subsystem_0783::Controller_0783;
        part controller_0784 : Subsystem_0784::Controller_0784;
        part controller_0785 : Subsystem_0785::Controller_0785;
        part controller_0786 : Subsystem_0786::Controller_0786;
        part controller_0787 : Subsystem_0787::Controller_0787;
        part controller_0788 : Subsystem_0788::Controller_0788;
        part controller_0789 : Subsystem_0789::Controller_0789;
        part controller_0790 : Subsystem_0790::Controller_0790;
        part controller_0791 : Subsystem_0791::Controller_0791;
        part controller_0792 : Subsystem_0792::Controller_0792;
        part controller_0793 : Subsystem_0793::Controller_0793;
        part controller_0794 : Subsystem_0794::Controller_0794;
        part controller_0795 : Subsystem_0795::Controller_0795;
        part controller_0796 : Subsystem_0796::Controller_0796;
        part controller_0797 : Subsystem_0797::Controller_0797;
        part controller_0798 : Subsystem_0798::Controller_0798;
        part controller_0799 : Subsystem_0799::Controller_0799;
        part controller_0800 : Subsystem_0800::Controller_0800;
        part controller_0801 : Subsystem_0801::Controller_0801;
        part controller_0802 : Subsystem_0802::Controller_0802;
        part controller_0803 : Subsystem_0803::Controller_0803;
        part controller_0804 : Subsystem_0804::Controller_0804;
        part controller_0805 : Subsystem_0805::Controller_0805;
        part controller_0806 : Subsystem_0806::Controller_0806;
        part controller_0807 : Subsystem_0807::Controller_0807;
        part controller_0808 : Subsystem_0808::Controller_0808;
        part controller_0809 : Subsystem_0809::Controller_0809;
        part controller_0810 : Subsystem_0810::Controller_0810;
        part controller_0811 : Subsystem_0811::Controller_0811;
        part controller_0812 : Subsystem_0812::Controller_0812;
        part controller_0813 : Subsystem_0813::Controller_0813;
        part controller_0814 : Subsystem_0814::Controller_0814;
        part controller_0815 : Subsystem_0815::Controller_0815;
        part controller_0816 : Subsystem_0816::Controller_0816;
        part controller_0817 : Subsystem_0817::Controller_0817;
        part controller_0818 : Subsystem_0818::Controller_0818;
        part controller_0819 : Subsystem_0819::Controller_0819;
        part controller_0820 : Subsystem_0820::Controller_0820;
        part controller_0821 : Subsystem_0821::Controller_0821;
        part controller_0822 : Subsystem_0822::Controller_0822;
        part controller_0823 : Subsystem_0823::Controller_0823;
        part controller_0824 : Subsystem_0824::Controller_0824;
        part controller_0825 : Subsystem_0825::Controller_0825;
        part controller_0826 : Subsystem_0826::Controller_0826;
        part controller_0827 : Subsystem_0827::Controller_0827;
        part controller_0828 : Subsystem_0828::Controller_0828;
        part controller_0829 : Subsystem_0829::Controller_0829;
        part controller_0830 : Subsystem_0830::Controller_0830;
        part controller_0831 : Subsystem_0831::Controller_0831;
        part controller_0832 : Subsystem_0832::Controller_0832;
        part controller_0833 : Subsystem_0833::Controller_0833;
        part controller_0834 : Subsystem_0834::Controller_0834;
        part controller_0835 : Subsystem_0835::Controller_0835;
        part controller_0836 : Subsystem_0836::Controller_0836;
        part controller_0837 : Subsystem_0837::Controller_0837;
        part controller_0838 : Subsystem_0838::Controller_0838;
        part controller_0839 : Subsystem_0839::Controller_0839;
        part controller_0840 : Subsystem_0840::Controller_0840;
        part controller_0841 : Subsystem_0841::Controller_0841;
        part controller_0842 : Subsystem_0842::Controller_0842;
        part controller_0843 : Subsystem_0843::Controller_0843;
        part controller_0844 : Subsystem_0844::Controller_0844;
        part controller_0845 : Subsystem_0845::Controller_0845;
        part controller_0846 : Subsystem_0846::Controller_0846;
        part controller_0847 : Subsystem_0847::Controller_0847;
        part controller_0848 : Subsystem_0848::Controller_0848;
        part controller_0849 : Subsystem_0849::Controller_0849;
        part controller_0850 : Subsystem_0850::Controller_0850;
        part controller_0851 : Subsystem_0851::Controller_0851;
        part controller_0852 : Subsystem_0852::Controller_0852;
        part controller_0853 : Subsystem_0853::Controller_0853;
        part controller_0854 : Subsystem_0854::Controller_0854;
        part controller_0855 : Subsystem_0855::Controller_0855;
        part controller_0856 : Subsystem_0856::Controller_0856;
        part controller_0857 : Subsystem_0857::Controller_0857;
        part controller_0858 : Subsystem_0858::Controller_0858;
        part controller_0859 : Subsystem_0859::Controller_0859;
        part controller_0860 : Subsystem_0860::Controller_0860;
        part controller_0861 : Subsystem_0861::Controller_0861;
        part controller_0862 : Subsystem_0862::Controller_0862;
        part controller_0863 : Subsystem_0863::Controller_0863;
        part controller_0864 : Subsystem_0864::Controller_0864;
        part controller_0865 : Subsystem_0865::Controller_0865;
        part controller_0866 : Subsystem_0866::Controller_0866;
        part controller_0867 : Subsystem_0867::Controller_0867;
        part controller_0868 : Subsystem_0868::Controller_0868;
        part controller_0869 : Subsystem_0869::Controller_0869;
        part controller_0870 : Subsystem_0870::Controller_0870;
        part controller_0871 : Subsystem_0871::Controller_0871;
        part controller_0872 : Subsystem_0872::Controller_0872;
        part controller_0873 : Subsystem_0873::Controller_0873;
        part controller_0874 : Subsystem_0874::Controller_0874;
        part controller_0875 : Subsystem_0875::Controller_0875;
        part controller_0876 : Subsystem_0876::Controller_0876;
        part controller_0877 : Subsystem_0877::Controller_0877;
        part controller_0878 : Subsystem_0878::Controller_0878;
        part controller_0879 : Subsystem_0879::Controller_0879;
        part controller_0880 : Subsystem_0880::Controller_0880;
        part controller_0881 : Subsystem_0881::Controller_0881;
        part controller_0882 : Subsystem_0882::Controller_0882;
        part controller_0883 : Subsystem_0883::Controller_0883;
        part controller_0884 : Subsystem_0884::Controller_0884;
        part controller_0885 : Subsystem_0885::Controller_0885;
        part controller_0886 : Subsystem_0886::Controller_0886;
        part controller_0887 : Subsystem_0887::Controller_0887;
        part controller_0888 : Subsystem_0888::Controller_0888;
        part controller_0889 : Subsystem_0889::Controller_0889;
        part controller_0890 : Subsystem_0890::Controller_0890;
        part controller_0891 : Subsystem_0891::Controller_0891;
        part controller_0892 : Subsystem_0892::Controller_0892;
        part controller_0893 : Subsystem_0893::Controller_0893;
        part controller_0894 : Subsystem_0894::Controller_0894;
        part controller_0895 : Subsystem_0895::Controller_0895;
        part controller_0896 : Subsystem_0896::Controller_0896;
        part controller_0897 : Subsystem_0897::Controller_0897;
        part controller_0898 : Subsystem_0898::Controller_0898;
        part controller_0899 : Subsystem_0899::Controller_0899;
        part controller_0900 : Subsystem_0900::Controller_0900;
        part controller_0901 : Subsystem_0901::Controller_0901;
        part controller_0902 : Subsystem_0902::Controller_0902;
        part controller_0903 : Subsystem_0903::Controller_0903;
        part controller_0904 : Subsystem_0904::Controller_0904;
        part controller_0905 : Subsystem_0905::Controller_0905;
        part controller_0906 : Subsystem_0906::Controller_0906;
        part controller_0907 : Subsystem_0907::Controller_0907;
        part controller_0908 : Subsystem_0908::Controller_0908;
        part controller_0909 : Subsystem_0909::Controller_0909;
        part controller_0910 : Subsystem_0910::Controller_0910;
        part controller_0911 : Subsystem_0911::Controller_0911;
        part controller_0912 : Subsystem_0912::Controller_0912;
        part controller_0913 : Subsystem_0913::Controller_0913;
        part controller_0914 : Subsystem_0914::Controller_0914;
        part controller_0915 : Subsystem_0915::Controller_0915;
        part controller_0916 : Subsystem_0916::Controller_0916;
        part controller_0917 : Subsystem_0917::Controller_0917;
        part controller_0918 : Subsystem_0918::Controller_0918;
        part controller_0919 : Subsystem_0919::Controller_0919;
        part controller_0920 : Subsystem_0920::Controller_0920;
        part controller_0921 : Subsystem_0921::Controller_0921;
        part controller_0922 : Subsystem_0922::Controller_0922;
        part controller_0923 : Subsystem_0923::Controller_0923;
        part controller_0924 : Subsystem_0924::Controller_0924;
        part controller_0925 : Subsystem_0925::Controller_0925;
        part controller_0926 : Subsystem_0926::Controller_0926;
        part controller_0927 : Subsystem_0927::Controller_0927;
        part controller_0928 : Subsystem_0928::Controller_0928;
        part controller_0929 : Subsystem_0929::Controller_0929;
        part controller_0930 : Subsystem_0930::Controller_0930;
        part controller_0931 : Subsystem_0931::Controller_0931;
        part controller_0932 : Subsystem_0932::Controller_0932;
        part controller_0933 : Subsystem_0933::Controller_0933;
        part controller_0934 : Subsystem_0934::Controller_0934;
        part controller_0935 : Subsystem_0935::Controller_0935;
        part controller_0936 : Subsystem_0936::Controller_0936;
        part controller_0937 : Subsystem_0937::Controller_0937;
        part controller_0938 : Subsystem_0938::Controller_0938;
        part controller_0939 : Subsystem_0939::Controller_0939;
        part controller_0940 : Subsystem_0940::Controller_0940;
        part controller_0941 : Subsystem_0941::Controller_0941;
        part controller_0942 : Subsystem_0942::Controller_0942;
        part controller_0943 : Subsystem_0943::Controller_0943;
        part controller_0944 : Subsystem_0944::Controller_0944;
        part controller_0945 : Subsystem_0945::Controller_0945;
        part controller_0946 : Subsystem_0946::Controller_0946;
        part controller_0947 : Subsystem_0947::Controller_0947;
        part controller_0948 : Subsystem_0948::Controller_0948;
        part controller_0949 : Subsystem_0949::Controller_0949;
        part controller_0950 : Subsystem_0950::Controller_0950;
        part controller_0951 : Subsystem_0951::Controller_0951;
        part controller_0952 : Subsystem_0952::Controller_0952;
        part controller_0953 : Subsystem_0953::Controller_0953;
        part controller_0954 : Subsystem_0954::Controller_0954;
        part controller_0955 : Subsystem_0955::Controller_0955;
        part controller_0956 : Subsystem_0956::Controller_0956;
        part controller_0957 : Subsystem_0957::Controller_0957;
        part controller_0958 : Subsystem_0958::Controller_0958;
        part controller_0959 : Subsystem_0959::Controller_0959;
        part controller_0960 : Subsystem_0960::Controller_0960;
        part controller_0961 : Subsystem_0961::Controller_0961;
        part controller_0962 : Subsystem_0962::Controller_0962;
        part controller_0963 : Subsystem_0963::Controller_0963;
        part controller_0964 : Subsystem_0964::Controller_0964;
        part controller_0965 : Subsystem_0965::Controller_0965;
        part controller_0966 : Subsystem_0966::Controller_0966;
        part controller_0967 : Subsystem_0967::Controller_0967;
        part controller_0968 : Subsystem_0968::Controller_0968;
        part controller_0969 : Subsystem_0969::Controller_0969;
        part controller_0970 : Subsystem_0970::Controller_0970;
        part controller_0971 : Subsystem_0971::Controller_0971;
        part controller_0972 : Subsystem_0972::Controller_0972;
        part controller_0973 : Subsystem_0973::Controller_0973;
        part controller_0974 : Subsystem_0974::Controller_0974;
        part controller_0975 : Subsystem_0975::Controller_0975;
        part controller_0976 : Subsystem_0976::Controller_0976;
        part controller_0977 : Subsystem_0977::Controller_0977;
        part controller_0978 : Subsystem_0978::Controller_0978;
        part controller_0979 : Subsystem_0979::Controller_0979;
        part controller_0980 : Subsystem_0980::Controller_0980;
        part controller_0981 : Subsystem_0981::Controller_0981;
        part controller_0982 : Subsystem_0982::Controller_0982;
        part controller_0983 : Subsystem_0983::Controller_0983;
        part controller_0984 : Subsystem_0984::Controller_0984;
        part controller_0985 : Subsystem_0985::Controller_0985;
        part controller_0986 : Subsystem_0986::Controller_0986;
        part controller_0987 : Subsystem_0987::Controller_0987;
        part controller_0988 : Subsystem_0988::Controller_0988;
        part controller_0989 : Subsystem_0989::Controller_0989;
        part controller_0990 : Subsystem_0990::Controller_0990;
        part controller_0991 : Subsystem_0991::Controller_0991;
        part controller_0992 : Subsystem_0992::Controller_0992;
        part controller_0993 : Subsystem_0993::Controller_0993;
        part controller_0994 : Subsystem_0994::Controller_0994;
        part controller_0995 : Subsystem_0995::Controller_0995;
        part controller_0996 : Subsystem_0996::Controller_0996;
        part controller_0997 : Subsystem_0997::Controller_0997;
        part controller_0998 : Subsystem_0998::Controller_0998;
        part controller_0999 : Subsystem_0999::Controller_0999;
        part controller_1000 : Subsystem_1000::Controller_1000;
        interface link_0001_0002 : Common::PowerLink connect
            source ::> controller_0001.supply to sink ::> controller_0002.power;
        interface link_0002_0003 : Common::PowerLink connect
            source ::> controller_0002.supply to sink ::> controller_0003.power;
        interface link_0003_0004 : Common::PowerLink connect
            source ::> controller_0003.supply to sink ::> controller_0004.power;
        interface link_0004_0005 : Common::PowerLink connect
            source ::> controller_0004.supply to sink ::> controller_0005.power;
        interface link_0005_0006 : Common::PowerLink connect
            source ::> controller_0005.supply to sink ::> controller_0006.power;
        interface link_0006_0007 : Common::PowerLink connect
            source ::> controller_0006.supply to sink ::> controller_0007.power;
        interface link_0007_0008 : Common::PowerLink connect
            source ::> controller_0007.supply to sink ::> controller_0008.power;
        interface link_0008_0009 : Common::PowerLink connect
            source ::> controller_0008.supply to sink ::> controller_0009.power;
        interface link_0009_0010 : Common::PowerLink connect
            source ::> controller_0009.supply to sink ::> controller_0010.power;
        interface link_0010_0011 : Common::PowerLink connect
            source ::> controller_0010.supply to sink ::> controller_0011.power;
        interface link_0011_0012 : Common::PowerLink connect
            source ::> controller_0011.supply to sink ::> controller_0012.power;
        interface link_0012_0013 : Common::PowerLink connect
            source ::> controller_0012.supply to sink ::> controller_0013.power;
        interface link_0013_0014 : Common::PowerLink connect
            source ::> controller_0013.supply to sink ::> controller_0014.power;
        interface link_0014_0015 : Common::PowerLink connect
            source ::> controller_0014.supply to sink ::> controller_0015.power;
        interface link_0015_0016 : Common::PowerLink connect
            source ::> controller_0015.supply to sink ::> controller_0016.power;
        interface link_0016_0017 : Common::PowerLink connect
            source ::> controller_0016.supply to sink ::> controller_0017.power;
        interface link_0017_0018 : Common::PowerLink connect
            source ::> controller_0017.supply to sink ::> controller_0018.power;
        interface link_0018_0019 : Common::PowerLink connect
            source ::> controller_0018.supply to sink ::> controller_0019.power;
        interface link_0019_0020 : Common::PowerLink connect
            source ::> controller_0019.supply to sink ::> controller_0020.power;
        interface link_0020_0021 : Common::PowerLink connect
            source ::> controller_0020.supply to sink ::> controller_0021.power;
        interface link_0021_0022 : Common::PowerLink connect
            source ::> controller_0021.supply to sink ::> controller_0022.power;
        interface link_0022_0023 : Common::PowerLink connect
            source ::> controller_0022.supply to sink ::> controller_0023.power;
        interface link_0023_0024 : Common::PowerLink connect
            source ::> controller_0023.supply to sink ::> controller_0024.power;
        interface link_0024_0025 : Common::PowerLink connect
            source ::> controller_0024.supply to sink ::> controller_0025.power;
        interface link_0025_0026 : Common::PowerLink connect
            source ::> controller_0025.supply to sink ::> controller_0026.power;
        interface link_0026_0027 : Common::PowerLink connect
            source ::> controller_0026.supply to sink ::> controller_0027.power;
        interface link_0027_0028 : Common::PowerLink connect
            source ::> controller_0027.supply to sink ::> controller_0028.power;
        interface link_0028_0029 : Common::PowerLink connect
            source ::> controller_0028.supply to sink ::> controller_0029.power;
        interface link_0029_0030 : Common::PowerLink connect
            source ::> controller_0029.supply to sink ::> controller_0030.power;
        interface link_0030_0031 : Common::PowerLink connect
            source ::> controller_0030.supply to sink ::> controller_0031.power;
        interface link_0031_0032 : Common::PowerLink connect
            source ::> controller_0031.supply to sink ::> controller_0032.power;
        interface link_0032_0033 : Common::PowerLink connect
            source ::> controller_0032.supply to sink ::> controller_0033.power;
        interface link_0033_0034 : Common::PowerLink connect
            source ::> controller_0033.supply to sink ::> controller_0034.power;
        interface link_0034_0035 : Common::PowerLink connect
            source ::> controller_0034.supply to sink ::> controller_0035.power;
        interface link_0035_0036 : Common::PowerLink connect
            source ::> controller_0035.supply to sink ::> controller_0036.power;
        interface link_0036_0037 : Common::PowerLink connect
            source ::> controller_0036.supply to sink ::> controller_0037.power;
        interface link_0037_0038 : Common::PowerLink connect
            source ::> controller_0037.supply to sink ::> controller_0038.power;
        interface link_0038_0039 : Common::PowerLink connect
            source ::> controller_0038.supply to sink ::> controller_0039.power;
        interface link_0039_0040 : Common::PowerLink connect
            source ::> controller_0039.supply to sink ::> controller_0040.power;
        interface link_0040_0041 : Common::PowerLink connect
            source ::> controller_0040.supply to sink ::> controller_0041.power;
        interface link_0041_0042 : Common::PowerLink connect
            source ::> controller_0041.supply to sink ::> controller_0042.power;
        interface link_0042_0043 : Common::PowerLink connect
            source ::> controller_0042.supply to sink ::> controller_0043.power;
        interface link_0043_0044 : Common::PowerLink connect
            source ::> controller_0043.supply to sink ::> controller_0044.power;
        interface link_0044_0045 : Common::PowerLink connect
            source ::> controller_0044.supply to sink ::> controller_0045.power;
        interface link_0045_0046 : Common::PowerLink connect
            source ::> controller_0045.supply to sink ::> controller_0046.power;
        interface link_0046_0047 : Common::PowerLink connect
            source ::> controller_0046.supply to sink ::> controller_0047.power;
        interface link_0047_0048 : Common::PowerLink connect
            source ::> controller_0047.supply to sink ::> controller_0048.power;
        interface link_0048_0049 : Common::PowerLink connect
            source ::> controller_0048.supply to sink ::> controller_0049.power;
        interface link_0049_0050 : Common::PowerLink connect
            source ::> controller_0049.supply to sink ::> controller_0050.power;
        interface link_0050_0051 : Common::PowerLink connect
            source ::> controller_0050.supply to sink ::> controller_0051.power;
        interface link_0051_0052 : Common::PowerLink connect
            source ::> controller_0051.supply to sink ::> controller_0052.power;
        interface link_0052_0053 : Common::PowerLink connect
            source ::> controller_0052.supply to sink ::> controller_0053.power;
        interface link_0053_0054 : Common::PowerLink connect
            source ::> controller_0053.supply to sink ::> controller_0054.power;
        interface link_0054_0055 : Common::PowerLink connect
            source ::> controller_0054.supply to sink ::> controller_0055.power;
        interface link_0055_0056 : Common::PowerLink connect
            source ::> controller_0055.supply to sink ::> controller_0056.power;
        interface link_0056_0057 : Common::PowerLink connect
            source ::> controller_0056.supply to sink ::> controller_0057.power;
        interface link_0057_0058 : Common::PowerLink connect
            source ::> controller_0057.supply to sink ::> controller_0058.power;
        interface link_0058_0059 : Common::PowerLink connect
            source ::> controller_0058.supply to sink ::> controller_0059.power;
        interface link_0059_0060 : Common::PowerLink connect
            source ::> controller_0059.supply to sink ::> controller_0060.power;
        interface link_0060_0061 : Common::PowerLink connect
            source ::> controller_0060.supply to sink ::> controller_0061.power;
        interface link_0061_0062 : Common::PowerLink connect
            source ::> controller_0061.supply to sink ::> controller_0062.power;
        interface link_0062_0063 : Common::PowerLink connect
            source ::> controller_0062.supply to sink ::> controller_0063.power;
        interface link_0063_0064 : Common::PowerLink connect
            source ::> controller_0063.supply to sink ::> controller_0064.power;
        interface link_0064_0065 : Common::PowerLink connect
            source ::> controller_0064.supply to sink ::> controller_0065.power;
        interface link_0065_0066 : Common::PowerLink connect
            source ::> controller_0065.supply to sink ::> controller_0066.power;
        interface link_0066_0067 : Common::PowerLink connect
            source ::> controller_0066.supply to sink ::> controller_0067.power;
        interface link_0067_0068 : Common::PowerLink connect
            source ::> controller_0067.supply to sink ::> controller_0068.power;
        interface link_0068_0069 : Common::PowerLink connect
            source ::> controller_0068.supply to sink ::> controller_0069.power;
        interface link_0069_0070 : Common::PowerLink connect
            source ::> controller_0069.supply to sink ::> controller_0070.power;
        interface link_0070_0071 : Common::PowerLink connect
            source ::> controller_0070.supply to sink ::> controller_0071.power;
        interface link_0071_0072 : Common::PowerLink connect
            source ::> controller_0071.supply to sink ::> controller_0072.power;
        interface link_0072_0073 : Common::PowerLink connect
            source ::> controller_0072.supply to sink ::> controller_0073.power;
        interface link_0073_0074 : Common::PowerLink connect
            source ::> controller_0073.supply to sink ::> controller_0074.power;
        interface link_0074_0075 : Common::PowerLink connect
            source ::> controller_0074.supply to sink ::> controller_0075.power;
        interface link_0075_0076 : Common::PowerLink connect
            source ::> controller_0075.supply to sink ::> controller_0076.power;
        interface link_0076_0077 : Common::PowerLink connect
            source ::> controller_0076.supply to sink ::> controller_0077.power;
        interface link_0077_0078 : Common::PowerLink connect
            source ::> controller_0077.supply to sink ::> controller_0078.power;
        interface link_0078_0079 : Common::PowerLink connect
            source ::> controller_0078.supply to sink ::> controller_0079.power;
        interface link_0079_0080 : Common::PowerLink connect
            source ::> controller_0079.supply to sink ::> controller_0080.power;
        interface link_0080_0081 : Common::PowerLink connect
            source ::> controller_0080.supply to sink ::> controller_0081.power;
        interface link_0081_0082 : Common::PowerLink connect
            source ::> controller_0081.supply to sink ::> controller_0082.power;
        interface link_0082_0083 : Common::PowerLink connect
            source ::> controller_0082.supply to sink ::> controller_0083.power;
        interface link_0083_0084 : Common::PowerLink connect
            source ::> controller_0083.supply to sink ::> controller_0084.power;
        interface link_0084_0085 : Common::PowerLink connect
            source ::> controller_0084.supply to sink ::> controller_0085.power;
        interface link_0085_0086 : Common::PowerLink connect
            source ::> controller_0085.supply to sink ::> controller_0086.power;
        interface link_0086_0087 : Common::PowerLink connect
            source ::> controller_0086.supply to sink ::> controller_0087.power;
        interface link_0087_0088 : Common::PowerLink connect
            source ::> controller_0087.supply to sink ::> controller_0088.power;
        interface link_0088_0089 : Common::PowerLink connect
            source ::> controller_0088.supply to sink ::> controller_0089.power;
        interface link_0089_0090 : Common::PowerLink connect
            source ::> controller_0089.supply to sink ::> controller_0090.power;
        interface link_0090_0091 : Common::PowerLink connect
            source ::> controller_0090.supply to sink ::> controller_0091.power;
        interface link_0091_0092 : Common::PowerLink connect
            source ::> controller_0091.supply to sink ::> controller_0092.power;
        interface link_0092_0093 : Common::PowerLink connect
            source ::> controller_0092.supply to sink ::> controller_0093.power;
        interface link_0093_0094 : Common::PowerLink connect
            source ::> controller_0093.supply to sink ::> controller_0094.power;
        interface link_0094_0095 : Common::PowerLink connect
            source ::> controller_0094.supply to sink ::> controller_0095.power;
        interface link_0095_0096 : Common::PowerLink connect
            source ::> controller_0095.supply to sink ::> controller_0096.power;
        interface link_0096_0097 : Common::PowerLink connect
            source ::> controller_0096.supply to sink ::> controller_0097.power;
        interface link_0097_0098 : Common::PowerLink connect
            source ::> controller_0097.supply to sink ::> controller_0098.power;
        interface link_0098_0099 : Common::PowerLink connect
            source ::> controller_0098.supply to sink ::> controller_0099.power;
        interface link_0099_0100 : Common::PowerLink connect
            source ::> controller_0099.supply to sink ::> controller_0100.power;
        interface link_0100_0101 : Common::PowerLink connect
            source ::> controller_0100.supply to sink ::> controller_0101.power;
        interface link_0101_0102 : Common::PowerLink connect
            source ::> controller_0101.supply to sink ::> controller_0102.power;
        interface link_0102_0103 : Common::PowerLink connect
            source ::> controller_0102.supply to sink ::> controller_0103.power;
        interface link_0103_0104 : Common::PowerLink connect
            source ::> controller_0103.supply to sink ::> controller_0104.power;
        interface link_0104_0105 : Common::PowerLink connect
            source ::> controller_0104.supply to sink ::> controller_0105.power;
        interface link_0105_0106 : Common::PowerLink connect
            source ::> controller_0105.supply to sink ::> controller_0106.power;
        interface link_0106_0107 : Common::PowerLink connect
            source ::> controller_0106.supply to sink ::> controller_0107.power;
        interface link_0107_0108 : Common::PowerLink connect
            source ::> controller_0107.supply to sink ::> controller_0108.power;
        interface link_0108_0109 : Common::PowerLink connect
            source ::> controller_0108.supply to sink ::> controller_0109.power;
        interface link_0109_0110 : Common::PowerLink connect
            source ::> controller_0109.supply to sink ::> controller_0110.power;
        interface link_0110_0111 : Common::PowerLink connect
            source ::> controller_0110.supply to sink ::> controller_0111.power;
        interface link_0111_0112 : Common::PowerLink connect
            source ::> controller_0111.supply to sink ::> controller_0112.power;
        interface link_0112_0113 : Common::PowerLink connect
            source ::> controller_0112.supply to sink ::> controller_0113.power;
        interface link_0113_0114 : Common::PowerLink connect
            source ::> controller_0113.supply to sink ::> controller_0114.power;
        interface link_0114_0115 : Common::PowerLink connect
            source ::> controller_0114.supply to sink ::> controller_0115.power;
        interface link_0115_0116 : Common::PowerLink connect
            source ::> controller_0115.supply to sink ::> controller_0116.power;
        interface link_0116_0117 : Common::PowerLink connect
            source ::> controller_0116.supply to sink ::> controller_0117.power;
        interface link_0117_0118 : Common::PowerLink connect
            source ::> controller_0117.supply to sink ::> controller_0118.power;
        interface link_0118_0119 : Common::PowerLink connect
            source ::> controller_0118.supply to sink ::> controller_0119.power;
        interface link_0119_0120 : Common::PowerLink connect
            source ::> controller_0119.supply to sink ::> controller_0120.power;
        interface link_0120_0121 : Common::PowerLink connect
            source ::> controller_0120.supply to sink ::> controller_0121.power;
        interface link_0121_0122 : Common::PowerLink connect
            source ::> controller_0121.supply to sink ::> controller_0122.power;
        interface link_0122_0123 : Common::PowerLink connect
            source ::> controller_0122.supply to sink ::> controller_0123.power;
        interface link_0123_0124 : Common::PowerLink connect
            source ::> controller_0123.supply to sink ::> controller_0124.power;
        interface link_0124_0125 : Common::PowerLink connect
            source ::> controller_0124.supply to sink ::> controller_0125.power;
        interface link_0125_0126 : Common::PowerLink connect
            source ::> controller_0125.supply to sink ::> controller_0126.power;
        interface link_0126_0127 : Common::PowerLink connect
            source ::> controller_0126.supply to sink ::> controller_0127.power;
        interface link_0127_0128 : Common::PowerLink connect
            source ::> controller_0127.supply to sink ::> controller_0128.power;
        interface link_0128_0129 : Common::PowerLink connect
            source ::> controller_0128.supply to sink ::> controller_0129.power;
        interface link_0129_0130 : Common::PowerLink connect
            source ::> controller_0129.supply to sink ::> controller_0130.power;
        interface link_0130_0131 : Common::PowerLink connect
            source ::> controller_0130.supply to sink ::> controller_0131.power;
        interface link_0131_0132 : Common::PowerLink connect
            source ::> controller_0131.supply to sink ::> controller_0132.power;
        interface link_0132_0133 : Common::PowerLink connect
            source ::> controller_0132.supply to sink ::> controller_0133.power;
        interface link_0133_0134 : Common::PowerLink connect
            source ::> controller_0133.supply to sink ::> controller_0134.power;
        interface link_0134_0135 : Common::PowerLink connect
            source ::> controller_0134.supply to sink ::> controller_0135.power;
        interface link_0135_0136 : Common::PowerLink connect
            source ::> controller_0135.supply to sink ::> controller_0136.power;
        interface link_0136_0137 : Common::PowerLink connect
            source ::> controller_0136.supply to sink ::> controller_0137.power;
        interface link_0137_0138 : Common::PowerLink connect
            source ::> controller_0137.supply to sink ::> controller_0138.power;
        interface link_0138_0139 : Common::PowerLink connect
            source ::> controller_0138.supply to sink ::> controller_0139.power;
        interface link_0139_0140 : Common::PowerLink connect
            source ::> controller_0139.supply to sink ::> controller_0140.power;
        interface link_0140_0141 : Common::PowerLink connect
            source ::> controller_0140.supply to sink ::> controller_0141.power;
        interface link_0141_0142 : Common::PowerLink connect
            source ::> controller_0141.supply to sink ::> controller_0142.power;
        interface link_0142_0143 : Common::PowerLink connect
            source ::> controller_0142.supply to sink ::> controller_0143.power;
        interface link_0143_0144 : Common::PowerLink connect
            source ::> controller_0143.supply to sink ::> controller_0144.power;
        interface link_0144_0145 : Common::PowerLink connect
            source ::> controller_0144.supply to sink ::> controller_0145.power;
        interface link_0145_0146 : Common::PowerLink connect
            source ::> controller_0145.supply to sink ::> controller_0146.power;
        interface link_0146_0147 : Common::PowerLink connect
            source ::> controller_0146.supply to sink ::> controller_0147.power;
        interface link_0147_0148 : Common::PowerLink connect
            source ::> controller_0147.supply to sink ::> controller_0148.power;
        interface link_0148_0149 : Common::PowerLink connect
            source ::> controller_0148.supply to sink ::> controller_0149.power;
        interface link_0149_0150 : Common::PowerLink connect
            source ::> controller_0149.supply to sink ::> controller_0150.power;
        interface link_0150_0151 : Common::PowerLink connect
            source ::> controller_0150.supply to sink ::> controller_0151.power;
        interface link_0151_0152 : Common::PowerLink connect
            source ::> controller_0151.supply to sink ::> controller_0152.power;
        interface link_0152_0153 : Common::PowerLink connect
            source ::> controller_0152.supply to sink ::> controller_0153.power;
        interface link_0153_0154 : Common::PowerLink connect
            source ::> controller_0153.supply to sink ::> controller_0154.power;
        interface link_0154_0155 : Common::PowerLink connect
            source ::> controller_0154.supply to sink ::> controller_0155.power;
        interface link_0155_0156 : Common::PowerLink connect
            source ::> controller_0155.supply to sink ::> controller_0156.power;
        interface link_0156_0157 : Common::PowerLink connect
            source ::> controller_0156.supply to sink ::> controller_0157.power;
        interface link_0157_0158 : Common::PowerLink connect
            source ::> controller_0157.supply to sink ::> controller_0158.power;
        interface link_0158_0159 : Common::PowerLink connect
            source ::> controller_0158.supply to sink ::> controller_0159.power;
        interface link_0159_0160 : Common::PowerLink connect
            source ::> controller_0159.supply to sink ::> controller_0160.power;
        interface link_0160_0161 : Common::PowerLink connect
            source ::> controller_0160.supply to sink ::> controller_0161.power;
        interface link_0161_0162 : Common::PowerLink connect
            source ::> controller_0161.supply to sink ::> controller_0162.power;
        interface link_0162_0163 : Common::PowerLink connect
            source ::> controller_0162.supply to sink ::> controller_0163.power;
        interface link_0163_0164 : Common::PowerLink connect
            source ::> controller_0163.supply to sink ::> controller_0164.power;
        interface link_0164_0165 : Common::PowerLink connect
            source ::> controller_0164.supply to sink ::> controller_0165.power;
        interface link_0165_0166 : Common::PowerLink connect
            source ::> controller_0165.supply to sink ::> controller_0166.power;
        interface link_0166_0167 : Common::PowerLink connect
            source ::> controller_0166.supply to sink ::> controller_0167.power;
        interface link_0167_0168 : Common::PowerLink connect
            source ::> controller_0167.supply to sink ::> controller_0168.power;
        interface link_0168_0169 : Common::PowerLink connect
            source ::> controller_0168.supply to sink ::> controller_0169.power;
        interface link_0169_0170 : Common::PowerLink connect
            source ::> controller_0169.supply to sink ::> controller_0170.power;
        interface link_0170_0171 : Common::PowerLink connect
            source ::> controller_0170.supply to sink ::> controller_0171.power;
        interface link_0171_0172 : Common::PowerLink connect
            source ::> controller_0171.supply to sink ::> controller_0172.power;
        interface link_0172_0173 : Common::PowerLink connect
            source ::> controller_0172.supply to sink ::> controller_0173.power;
        interface link_0173_0174 : Common::PowerLink connect
            source ::> controller_0173.supply to sink ::> controller_0174.power;
        interface link_0174_0175 : Common::PowerLink connect
            source ::> controller_0174.supply to sink ::> controller_0175.power;
        interface link_0175_0176 : Common::PowerLink connect
            source ::> controller_0175.supply to sink ::> controller_0176.power;
        interface link_0176_0177 : Common::PowerLink connect
            source ::> controller_0176.supply to sink ::> controller_0177.power;
        interface link_0177_0178 : Common::PowerLink connect
            source ::> controller_0177.supply to sink ::> controller_0178.power;
        interface link_0178_0179 : Common::PowerLink connect
            source ::> controller_0178.supply to sink ::> controller_0179.power;
        interface link_0179_0180 : Common::PowerLink connect
            source ::> controller_0179.supply to sink ::> controller_0180.power;
        interface link_0180_0181 : Common::PowerLink connect
            source ::> controller_0180.supply to sink ::> controller_0181.power;
        interface link_0181_0182 : Common::PowerLink connect
            source ::> controller_0181.supply to sink ::> controller_0182.power;
        interface link_0182_0183 : Common::PowerLink connect
            source ::> controller_0182.supply to sink ::> controller_0183.power;
        interface link_0183_0184 : Common::PowerLink connect
            source ::> controller_0183.supply to sink ::> controller_0184.power;
        interface link_0184_0185 : Common::PowerLink connect
            source ::> controller_0184.supply to sink ::> controller_0185.power;
        interface link_0185_0186 : Common::PowerLink connect
            source ::> controller_0185.supply to sink ::> controller_0186.power;
        interface link_0186_0187 : Common::PowerLink connect
            source ::> controller_0186.supply to sink ::> controller_0187.power;
        interface link_0187_0188 : Common::PowerLink connect
            source ::> controller_0187.supply to sink ::> controller_0188.power;
        interface link_0188_0189 : Common::PowerLink connect
            source ::> controller_0188.supply to sink ::> controller_0189.power;
        interface link_0189_0190 : Common::PowerLink connect
            source ::> controller_0189.supply to sink ::> controller_0190.power;
        interface link_0190_0191 : Common::PowerLink connect
            source ::> controller_0190.supply to sink ::> controller_0191.power;
        interface link_0191_0192 : Common::PowerLink connect
            source ::> controller_0191.supply to sink ::> controller_0192.power;
        interface link_0192_0193 : Common::PowerLink connect
            source ::> controller_0192.supply to sink ::> controller_0193.power;
        interface link_0193_0194 : Common::PowerLink connect
            source ::> controller_0193.supply to sink ::> controller_0194.power;
        interface link_0194_0195 : Common::PowerLink connect
            source ::> controller_0194.supply to sink ::> controller_0195.power;
        interface link_0195_0196 : Common::PowerLink connect
            source ::> controller_0195.supply to sink ::> controller_0196.power;
        interface link_0196_0197 : Common::PowerLink connect
            source ::> controller_0196.supply to sink ::> controller_0197.power;
        interface link_0197_0198 : Common::PowerLink connect
            source ::> controller_0197.supply to sink ::> controller_0198.power;
        interface link_0198_0199 : Common::PowerLink connect
            source ::> controller_0198.supply to sink ::> controller_0199.power;
        interface link_0199_0200 : Common::PowerLink connect
            source ::> controller_0199.supply to sink ::> controller_0200.power;
        interface link_0200_0201 : Common::PowerLink connect
            source ::> controller_0200.supply to sink ::> controller_0201.power;
        interface link_0201_0202 : Common::PowerLink connect
            source ::> controller_0201.supply to sink ::> controller_0202.power;
        interface link_0202_0203 : Common::PowerLink connect
            source ::> controller_0202.supply to sink ::> controller_0203.power;
        interface link_0203_0204 : Common::PowerLink connect
            source ::> controller_0203.supply to sink ::> controller_0204.power;
        interface link_0204_0205 : Common::PowerLink connect
            source ::> controller_0204.supply to sink ::> controller_0205.power;
        interface link_0205_0206 : Common::PowerLink connect
            source ::> controller_0205.supply to sink ::> controller_0206.power;
        interface link_0206_0207 : Common::PowerLink connect
            source ::> controller_0206.supply to sink ::> controller_0207.power;
        interface link_0207_0208 : Common::PowerLink connect
            source ::> controller_0207.supply to sink ::> controller_0208.power;
        interface link_0208_0209 : Common::PowerLink connect
            source ::> controller_0208.supply to sink ::> controller_0209.power;
        interface link_0209_0210 : Common::PowerLink connect
            source ::> controller_0209.supply to sink ::> controller_0210.power;
        interface link_0210_0211 : Common::PowerLink connect
            source ::> controller_0210.supply to sink ::> controller_0211.power;
        interface link_0211_0212 : Common::PowerLink connect
            source ::> controller_0211.supply to sink ::> controller_0212.power;
        interface link_0212_0213 : Common::PowerLink connect
            source ::> controller_0212.supply to sink ::> controller_0213.power;
        interface link_0213_0214 : Common::PowerLink connect
            source ::> controller_0213.supply to sink ::> controller_0214.power;
        interface link_0214_0215 : Common::PowerLink connect
            source ::> controller_0214.supply to sink ::> controller_0215.power;
        interface link_0215_0216 : Common::PowerLink connect
            source ::> controller_0215.supply to sink ::> controller_0216.power;
        interface link_0216_0217 : Common::PowerLink connect
            source ::> controller_0216.supply to sink ::> controller_0217.power;
        interface link_0217_0218 : Common::PowerLink connect
            source ::> controller_0217.supply to sink ::> controller_0218.power;
        interface link_0218_0219 : Common::PowerLink connect
            source ::> controller_0218.supply to sink ::> controller_0219.power;
        interface link_0219_0220 : Common::PowerLink connect
            source ::> controller_0219.supply to sink ::> controller_0220.power;
        interface link_0220_0221 : Common::PowerLink connect
            source ::> controller_0220.supply to sink ::> controller_0221.power;
        interface link_0221_0222 : Common::PowerLink connect
            source ::> controller_0221.supply to sink ::> controller_0222.power;
        interface link_0222_0223 : Common::PowerLink connect
            source ::> controller_0222.supply to sink ::> controller_0223.power;
        interface link_0223_0224 : Common::PowerLink connect
            source ::> controller_0223.supply to sink ::> controller_0224.power;
        interface link_0224_0225 : Common::PowerLink connect
            source ::> controller_0224.supply to sink ::> controller_0225.power;
        interface link_0225_0226 : Common::PowerLink connect
            source ::> controller_0225.supply to sink ::> controller_0226.power;
        interface link_0226_0227 : Common::PowerLink connect
            source ::> controller_0226.supply to sink ::> controller_0227.power;
        interface link_0227_0228 : Common::PowerLink connect
            source ::> controller_0227.supply to sink ::> controller_0228.power;
        interface link_0228_0229 : Common::PowerLink connect
            source ::> controller_0228.supply to sink ::> controller_0229.power;
        interface link_0229_0230 : Common::PowerLink connect
            source ::> controller_0229.supply to sink ::> controller_0230.power;
        interface link_0230_0231 : Common::PowerLink connect
            source ::> controller_0230.supply to sink ::> controller_0231.power;
        interface link_0231_0232 : Common::PowerLink connect
            source ::> controller_0231.supply to sink ::> controller_0232.power;
        interface link_0232_0233 : Common::PowerLink connect
            source ::> controller_0232.supply to sink ::> controller_0233.power;
        interface link_0233_0234 : Common::PowerLink connect
            source ::> controller_0233.supply to sink ::> controller_0234.power;
        interface link_0234_0235 : Common::PowerLink connect
            source ::> controller_0234.supply to sink ::> controller_0235.power;
        interface link_0235_0236 : Common::PowerLink connect
            source ::> controller_0235.supply to sink ::> controller_0236.power;
        interface link_0236_0237 : Common::PowerLink connect
            source ::> controller_0236.supply to sink ::> controller_0237.power;
        interface link_0237_0238 : Common::PowerLink connect
            source ::> controller_0237.supply to sink ::> controller_0238.power;
        interface link_0238_0239 : Common::PowerLink connect
            source ::> controller_0238.supply to sink ::> controller_0239.power;
        interface link_0239_0240 : Common::PowerLink connect
            source ::> controller_0239.supply to sink ::> controller_0240.power;
        interface link_0240_0241 : Common::PowerLink connect
            source ::> controller_0240.supply to sink ::> controller_0241.power;
        interface link_0241_0242 : Common::PowerLink connect
            source ::> controller_0241.supply to sink ::> controller_0242.power;
        interface link_0242_0243 : Common::PowerLink connect
            source ::> controller_0242.supply to sink ::> controller_0243.power;
        interface link_0243_0244 : Common::PowerLink connect
            source ::> controller_0243.supply to sink ::> controller_0244.power;
        interface link_0244_0245 : Common::PowerLink connect
            source ::> controller_0244.supply to sink ::> controller_0245.power;
        interface link_0245_0246 : Common::PowerLink connect
            source ::> controller_0245.supply to sink ::> controller_0246.power;
        interface link_0246_0247 : Common::PowerLink connect
            source ::> controller_0246.supply to sink ::> controller_0247.power;
        interface link_0247_0248 : Common::PowerLink connect
            source ::> controller_0247.supply to sink ::> controller_0248.power;
        interface link_0248_0249 : Common::PowerLink connect
            source ::> controller_0248.supply to sink ::> controller_0249.power;
        interface link_0249_0250 : Common::PowerLink connect
            source ::> controller_0249.supply to sink ::> controller_0250.power;
        interface link_0250_0251 : Common::PowerLink connect
            source ::> controller_0250.supply to sink ::> controller_0251.power;
        interface link_0251_0252 : Common::PowerLink connect
            source ::> controller_0251.supply to sink ::> controller_0252.power;
        interface link_0252_0253 : Common::PowerLink connect
            source ::> controller_0252.supply to sink ::> controller_0253.power;
        interface link_0253_0254 : Common::PowerLink connect
            source ::> controller_0253.supply to sink ::> controller_0254.power;
        interface link_0254_0255 : Common::PowerLink connect
            source ::> controller_0254.supply to sink ::> controller_0255.power;
        interface link_0255_0256 : Common::PowerLink connect
            source ::> controller_0255.supply to sink ::> controller_0256.power;
        interface link_0256_0257 : Common::PowerLink connect
            source ::> controller_0256.supply to sink ::> controller_0257.power;
        interface link_0257_0258 : Common::PowerLink connect
            source ::> controller_0257.supply to sink ::> controller_0258.power;
        interface link_0258_0259 : Common::PowerLink connect
            source ::> controller_0258.supply to sink ::> controller_0259.power;
        interface link_0259_0260 : Common::PowerLink connect
            source ::> controller_0259.supply to sink ::> controller_0260.power;
        interface link_0260_0261 : Common::PowerLink connect
            source ::> controller_0260.supply to sink ::> controller_0261.power;
        interface link_0261_0262 : Common::PowerLink connect
            source ::> controller_0261.supply to sink ::> controller_0262.power;
        interface link_0262_0263 : Common::PowerLink connect
            source ::> controller_0262.supply to sink ::> controller_0263.power;
        interface link_0263_0264 : Common::PowerLink connect
            source ::> controller_0263.supply to sink ::> controller_0264.power;
        interface link_0264_0265 : Common::PowerLink connect
            source ::> controller_0264.supply to sink ::> controller_0265.power;
        interface link_0265_0266 : Common::PowerLink connect
            source ::> controller_0265.supply to sink ::> controller_0266.power;
        interface link_0266_0267 : Common::PowerLink connect
            source ::> controller_0266.supply to sink ::> controller_0267.power;
        interface link_0267_0268 : Common::PowerLink connect
            source ::> controller_0267.supply to sink ::> controller_0268.power;
        interface link_0268_0269 : Common::PowerLink connect
            source ::> controller_0268.supply to sink ::> controller_0269.power;
        interface link_0269_0270 : Common::PowerLink connect
            source ::> controller_0269.supply to sink ::> controller_0270.power;
        interface link_0270_0271 : Common::PowerLink connect
            source ::> controller_0270.supply to sink ::> controller_0271.power;
        interface link_0271_0272 : Common::PowerLink connect
            source ::> controller_0271.supply to sink ::> controller_0272.power;
        interface link_0272_0273 : Common::PowerLink connect
            source ::> controller_0272.supply to sink ::> controller_0273.power;
        interface link_0273_0274 : Common::PowerLink connect
            source ::> controller_0273.supply to sink ::> controller_0274.power;
        interface link_0274_0275 : Common::PowerLink connect
            source ::> controller_0274.supply to sink ::> controller_0275.power;
        interface link_0275_0276 : Common::PowerLink connect
            source ::> controller_0275.supply to sink ::> controller_0276.power;
        interface link_0276_0277 : Common::PowerLink connect
            source ::> controller_0276.supply to sink ::> controller_0277.power;
        interface link_0277_0278 : Common::PowerLink connect
            source ::> controller_0277.supply to sink ::> controller_0278.power;
        interface link_0278_0279 : Common::PowerLink connect
            source ::> controller_0278.supply to sink ::> controller_0279.power;
        interface link_0279_0280 : Common::PowerLink connect
            source ::> controller_0279.supply to sink ::> controller_0280.power;
        interface link_0280_0281 : Common::PowerLink connect
            source ::> controller_0280.supply to sink ::> controller_0281.power;
        interface link_0281_0282 : Common::PowerLink connect
            source ::> controller_0281.supply to sink ::> controller_0282.power;
        interface link_0282_0283 : Common::PowerLink connect
            source ::> controller_0282.supply to sink ::> controller_0283.power;
        interface link_0283_0284 : Common::PowerLink connect
            source ::> controller_0283.supply to sink ::> controller_0284.power;
        interface link_0284_0285 : Common::PowerLink connect
            source ::> controller_0284.supply to sink ::> controller_0285.power;
        interface link_0285_0286 : Common::PowerLink connect
            source ::> controller_0285.supply to sink ::> controller_0286.power;
        interface link_0286_0287 : Common::PowerLink connect
            source ::> controller_0286.supply to sink ::> controller_0287.power;
        interface link_0287_0288 : Common::PowerLink connect
            source ::> controller_0287.supply to sink ::> controller_0288.power;
        interface link_0288_0289 : Common::PowerLink connect
            source ::> controller_0288.supply to sink ::> controller_0289.power;
        interface link_0289_0290 : Common::PowerLink connect
            source ::> controller_0289.supply to sink ::> controller_0290.power;
        interface link_0290_0291 : Common::PowerLink connect
            source ::> controller_0290.supply to sink ::> controller_0291.power;
        interface link_0291_0292 : Common::PowerLink connect
            source ::> controller_0291.supply to sink ::> controller_0292.power;
        interface link_0292_0293 : Common::PowerLink connect
            source ::> controller_0292.supply to sink ::> controller_0293.power;
        interface link_0293_0294 : Common::PowerLink connect
            source ::> controller_0293.supply to sink ::> controller_0294.power;
        interface link_0294_0295 : Common::PowerLink connect
            source ::> controller_0294.supply to sink ::> controller_0295.power;
        interface link_0295_0296 : Common::PowerLink connect
            source ::> controller_0295.supply to sink ::> controller_0296.power;
        interface link_0296_0297 : Common::PowerLink connect
            source ::> controller_0296.supply to sink ::> controller_0297.power;
        interface link_0297_0298 : Common::PowerLink connect
            source ::> controller_0297.supply to sink ::> controller_0298.power;
        interface link_0298_0299 : Common::PowerLink connect
            source ::> controller_0298.supply to sink ::> controller_0299.power;
        interface link_0299_0300 : Common::PowerLink connect
            source ::> controller_0299.supply to sink ::> controller_0300.power;
        interface link_0300_0301 : Common::PowerLink connect
            source ::> controller_0300.supply to sink ::> controller_0301.power;
        interface link_0301_0302 : Common::PowerLink connect
            source ::> controller_0301.supply to sink ::> controller_0302.power;
        interface link_0302_0303 : Common::PowerLink connect
            source ::> controller_0302.supply to sink ::> controller_0303.power;
        interface link_0303_0304 : Common::PowerLink connect
            source ::> controller_0303.supply to sink ::> controller_0304.power;
        interface link_0304_0305 : Common::PowerLink connect
            source ::> controller_0304.supply to sink ::> controller_0305.power;
        interface link_0305_0306 : Common::PowerLink connect
            source ::> controller_0305.supply to sink ::> controller_0306.power;
        interface link_0306_0307 : Common::PowerLink connect
            source ::> controller_0306.supply to sink ::> controller_0307.power;
        interface link_0307_0308 : Common::PowerLink connect
            source ::> controller_0307.supply to sink ::> controller_0308.power;
        interface link_0308_0309 : Common::PowerLink connect
            source ::> controller_0308.supply to sink ::> controller_0309.power;
        interface link_0309_0310 : Common::PowerLink connect
            source ::> controller_0309.supply to sink ::> controller_0310.power;
        interface link_0310_0311 : Common::PowerLink connect
            source ::> controller_0310.supply to sink ::> controller_0311.power;
        interface link_0311_0312 : Common::PowerLink connect
            source ::> controller_0311.supply to sink ::> controller_0312.power;
        interface link_0312_0313 : Common::PowerLink connect
            source ::> controller_0312.supply to sink ::> controller_0313.power;
        interface link_0313_0314 : Common::PowerLink connect
            source ::> controller_0313.supply to sink ::> controller_0314.power;
        interface link_0314_0315 : Common::PowerLink connect
            source ::> controller_0314.supply to sink ::> controller_0315.power;
        interface link_0315_0316 : Common::PowerLink connect
            source ::> controller_0315.supply to sink ::> controller_0316.power;
        interface link_0316_0317 : Common::PowerLink connect
            source ::> controller_0316.supply to sink ::> controller_0317.power;
        interface link_0317_0318 : Common::PowerLink connect
            source ::> controller_0317.supply to sink ::> controller_0318.power;
        interface link_0318_0319 : Common::PowerLink connect
            source ::> controller_0318.supply to sink ::> controller_0319.power;
        interface link_0319_0320 : Common::PowerLink connect
            source ::> controller_0319.supply to sink ::> controller_0320.power;
        interface link_0320_0321 : Common::PowerLink connect
            source ::> controller_0320.supply to sink ::> controller_0321.power;
        interface link_0321_0322 : Common::PowerLink connect
            source ::> controller_0321.supply to sink ::> controller_0322.power;
        interface link_0322_0323 : Common::PowerLink connect
            source ::> controller_0322.supply to sink ::> controller_0323.power;
        interface link_0323_0324 : Common::PowerLink connect
            source ::> controller_0323.supply to sink ::> controller_0324.power;
        interface link_0324_0325 : Common::PowerLink connect
            source ::> controller_0324.supply to sink ::> controller_0325.power;
        interface link_0325_0326 : Common::PowerLink connect
            source ::> controller_0325.supply to sink ::> controller_0326.power;
        interface link_0326_0327 : Common::PowerLink connect
            source ::> controller_0326.supply to sink ::> controller_0327.power;
        interface link_0327_0328 : Common::PowerLink connect
            source ::> controller_0327.supply to sink ::> controller_0328.power;
        interface link_0328_0329 : Common::PowerLink connect
            source ::> controller_0328.supply to sink ::> controller_0329.power;
        interface link_0329_0330 : Common::PowerLink connect
            source ::> controller_0329.supply to sink ::> controller_0330.power;
        interface link_0330_0331 : Common::PowerLink connect
            source ::> controller_0330.supply to sink ::> controller_0331.power;
        interface link_0331_0332 : Common::PowerLink connect
            source ::> controller_0331.supply to sink ::> controller_0332.power;
        interface link_0332_0333 : Common::PowerLink connect
            source ::> controller_0332.supply to sink ::> controller_0333.power;
        interface link_0333_0334 : Common::PowerLink connect
            source ::> controller_0333.supply to sink ::> controller_0334.power;
        interface link_0334_0335 : Common::PowerLink connect
            source ::> controller_0334.supply to sink ::> controller_0335.power;
        interface link_0335_0336 : Common::PowerLink connect
            source ::> controller_0335.supply to sink ::> controller_0336.power;
        interface link_0336_0337 : Common::PowerLink connect
            source ::> controller_0336.supply to sink ::> controller_0337.power;
        interface link_0337_0338 : Common::PowerLink connect
            source ::> controller_0337.supply to sink ::> controller_0338.power;
        interface link_0338_0339 : Common::PowerLink connect
            source ::> controller_0338.supply to sink ::> controller_0339.power;
        interface link_0339_0340 : Common::PowerLink connect
            source ::> controller_0339.supply to sink ::> controller_0340.power;
        interface link_0340_0341 : Common::PowerLink connect
            source ::> controller_0340.supply to sink ::> controller_0341.power;
        interface link_0341_0342 : Common::PowerLink connect
            source ::> controller_0341.supply to sink ::> controller_0342.power;
        interface link_0342_0343 : Common::PowerLink connect
            source ::> controller_0342.supply to sink ::> controller_0343.power;
        interface link_0343_0344 : Common::PowerLink connect
            source ::> controller_0343.supply to sink ::> controller_0344.power;
        interface link_0344_0345 : Common::PowerLink connect
            source ::> controller_0344.supply to sink ::> controller_0345.power;
        interface link_0345_0346 : Common::PowerLink connect
            source ::> controller_0345.supply to sink ::> controller_0346.power;
        interface link_0346_0347 : Common::PowerLink connect
            source ::> controller_0346.supply to sink ::> controller_0347.power;
        interface link_0347_0348 : Common::PowerLink connect
            source ::> controller_0347.supply to sink ::> controller_0348.power;
        interface link_0348_0349 : Common::PowerLink connect
            source ::> controller_0348.supply to sink ::> controller_0349.power;
        interface link_0349_0350 : Common::PowerLink connect
            source ::> controller_0349.supply to sink ::> controller_0350.power;
        interface link_0350_0351 : Common::PowerLink connect
            source ::> controller_0350.supply to sink ::> controller_0351.power;
        interface link_0351_0352 : Common::PowerLink connect
            source ::> controller_0351.supply to sink ::> controller_0352.power;
        interface link_0352_0353 : Common::PowerLink connect
            source ::> controller_0352.supply to sink ::> controller_0353.power;
        interface link_0353_0354 : Common::PowerLink connect
            source ::> controller_0353.supply to sink ::> controller_0354.power;
        interface link_0354_0355 : Common::PowerLink connect
            source ::> controller_0354.supply to sink ::> controller_0355.power;
        interface link_0355_0356 : Common::PowerLink connect
            source ::> controller_0355.supply to sink ::> controller_0356.power;
        interface link_0356_0357 : Common::PowerLink connect
            source ::> controller_0356.supply to sink ::> controller_0357.power;
        interface link_0357_0358 : Common::PowerLink connect
            source ::> controller_0357.supply to sink ::> controller_0358.power;
        interface link_0358_0359 : Common::PowerLink connect
            source ::> controller_0358.supply to sink ::> controller_0359.power;
        interface link_0359_0360 : Common::PowerLink connect
            source ::> controller_0359.supply to sink ::> controller_0360.power;
        interface link_0360_0361 : Common::PowerLink connect
            source ::> controller_0360.supply to sink ::> controller_0361.power;
        interface link_0361_0362 : Common::PowerLink connect
            source ::> controller_0361.supply to sink ::> controller_0362.power;
        interface link_0362_0363 : Common::PowerLink connect
            source ::> controller_0362.supply to sink ::> controller_0363.power;
        interface link_0363_0364 : Common::PowerLink connect
            source ::> controller_0363.supply to sink ::> controller_0364.power;
        interface link_0364_0365 : Common::PowerLink connect
            source ::> controller_0364.supply to sink ::> controller_0365.power;
        interface link_0365_0366 : Common::PowerLink connect
            source ::> controller_0365.supply to sink ::> controller_0366.power;
        interface link_0366_0367 : Common::PowerLink connect
            source ::> controller_0366.supply to sink ::> controller_0367.power;
        interface link_0367_0368 : Common::PowerLink connect
            source ::> controller_0367.supply to sink ::> controller_0368.power;
        interface link_0368_0369 : Common::PowerLink connect
            source ::> controller_0368.supply to sink ::> controller_0369.power;
        interface link_0369_0370 : Common::PowerLink connect
            source ::> controller_0369.supply to sink ::> controller_0370.power;
        interface link_0370_0371 : Common::PowerLink connect
            source ::> controller_0370.supply to sink ::> controller_0371.power;
        interface link_0371_0372 : Common::PowerLink connect
            source ::> controller_0371.supply to sink ::> controller_0372.power;
        interface link_0372_0373 : Common::PowerLink connect
            source ::> controller_0372.supply to sink ::> controller_0373.power;
        interface link_0373_0374 : Common::PowerLink connect
            source ::> controller_0373.supply to sink ::> controller_0374.power;
        interface link_0374_0375 : Common::PowerLink connect
            source ::> controller_0374.supply to sink ::> controller_0375.power;
        interface link_0375_0376 : Common::PowerLink connect
            source ::> controller_0375.supply to sink ::> controller_0376.power;
        interface link_0376_0377 : Common::PowerLink connect
            source ::> controller_0376.supply to sink ::> controller_0377.power;
        interface link_0377_0378 : Common::PowerLink connect
            source ::> controller_0377.supply to sink ::> controller_0378.power;
        interface link_0378_0379 : Common::PowerLink connect
            source ::> controller_0378.supply to sink ::> controller_0379.power;
        interface link_0379_0380 : Common::PowerLink connect
            source ::> controller_0379.supply to sink ::> controller_0380.power;
        interface link_0380_0381 : Common::PowerLink connect
            source ::> controller_0380.supply to sink ::> controller_0381.power;
        interface link_0381_0382 : Common::PowerLink connect
            source ::> controller_0381.supply to sink ::> controller_0382.power;
        interface link_0382_0383 : Common::PowerLink connect
            source ::> controller_0382.supply to sink ::> controller_0383.power;
        interface link_0383_0384 : Common::PowerLink connect
            source ::> controller_0383.supply to sink ::> controller_0384.power;
        interface link_0384_0385 : Common::PowerLink connect
            source ::> controller_0384.supply to sink ::> controller_0385.power;
        interface link_0385_0386 : Common::PowerLink connect
            source ::> controller_0385.supply to sink ::> controller_0386.power;
        interface link_0386_0387 : Common::PowerLink connect
            source ::> controller_0386.supply to sink ::> controller_0387.power;
        interface link_0387_0388 : Common::PowerLink connect
            source ::> controller_0387.supply to sink ::> controller_0388.power;
        interface link_0388_0389 : Common::PowerLink connect
            source ::> controller_0388.supply to sink ::> controller_0389.power;
        interface link_0389_0390 : Common::PowerLink connect
            source ::> controller_0389.supply to sink ::> controller_0390.power;
        interface link_0390_0391 : Common::PowerLink connect
            source ::> controller_0390.supply to sink ::> controller_0391.power;
        interface link_0391_0392 : Common::PowerLink connect
            source ::> controller_0391.supply to sink ::> controller_0392.power;
        interface link_0392_0393 : Common::PowerLink connect
            source ::> controller_0392.supply to sink ::> controller_0393.power;
        interface link_0393_0394 : Common::PowerLink connect
            source ::> controller_0393.supply to sink ::> controller_0394.power;
        interface link_0394_0395 : Common::PowerLink connect
            source ::> controller_0394.supply to sink ::> controller_0395.power;
        interface link_0395_0396 : Common::PowerLink connect
            source ::> controller_0395.supply to sink ::> controller_0396.power;
        interface link_0396_0397 : Common::PowerLink connect
            source ::> controller_0396.supply to sink ::> controller_0397.power;
        interface link_0397_0398 : Common::PowerLink connect
            source ::> controller_0397.supply to sink ::> controller_0398.power;
        interface link_0398_0399 : Common::PowerLink connect
            source ::> controller_0398.supply to sink ::> controller_0399.power;
        interface link_0399_0400 : Common::PowerLink connect
            source ::> controller_0399.supply to sink ::> controller_0400.power;
        interface link_0400_0401 : Common::PowerLink connect
            source ::> controller_0400.supply to sink ::> controller_0401.power;
        interface link_0401_0402 : Common::PowerLink connect
            source ::> controller_0401.supply to sink ::> controller_0402.power;
        interface link_0402_0403 : Common::PowerLink connect
            source ::> controller_0402.supply to sink ::> controller_0403.power;
        interface link_0403_0404 : Common::PowerLink connect
            source ::> controller_0403.supply to sink ::> controller_0404.power;
        interface link_0404_0405 : Common::PowerLink connect
            source ::> controller_0404.supply to sink ::> controller_0405.power;
        interface link_0405_0406 : Common::PowerLink connect
            source ::> controller_0405.supply to sink ::> controller_0406.power;
        interface link_0406_0407 : Common::PowerLink connect
            source ::> controller_0406.supply to sink ::> controller_0407.power;
        interface link_0407_0408 : Common::PowerLink connect
            source ::> controller_0407.supply to sink ::> controller_0408.power;
        interface link_0408_0409 : Common::PowerLink connect
            source ::> controller_0408.supply to sink ::> controller_0409.power;
        interface link_0409_0410 : Common::PowerLink connect
            source ::> controller_0409.supply to sink ::> controller_0410.power;
        interface link_0410_0411 : Common::PowerLink connect
            source ::> controller_0410.supply to sink ::> controller_0411.power;
        interface link_0411_0412 : Common::PowerLink connect
            source ::> controller_0411.supply to sink ::> controller_0412.power;
        interface link_0412_0413 : Common::PowerLink connect
            source ::> controller_0412.supply to sink ::> controller_0413.power;
        interface link_0413_0414 : Common::PowerLink connect
            source ::> controller_0413.supply to sink ::> controller_0414.power;
        interface link_0414_0415 : Common::PowerLink connect
            source ::> controller_0414.supply to sink ::> controller_0415.power;
        interface link_0415_0416 : Common::PowerLink connect
            source ::> controller_0415.supply to sink ::> controller_0416.power;
        interface link_0416_0417 : Common::PowerLink connect
            source ::> controller_0416.supply to sink ::> controller_0417.power;
        interface link_0417_0418 : Common::PowerLink connect
            source ::> controller_0417.supply to sink ::> controller_0418.power;
        interface link_0418_0419 : Common::PowerLink connect
            source ::> controller_0418.supply to sink ::> controller_0419.power;
        interface link_0419_0420 : Common::PowerLink connect
            source ::> controller_0419.supply to sink ::> controller_0420.power;
        interface link_0420_0421 : Common::PowerLink connect
            source ::> controller_0420.supply to sink ::> controller_0421.power;
        interface link_0421_0422 : Common::PowerLink connect
            source ::> controller_0421.supply to sink ::> controller_0422.power;
        interface link_0422_0423 : Common::PowerLink connect
            source ::> controller_0422.supply to sink ::> controller_0423.power;
        interface link_0423_0424 : Common::PowerLink connect
            source ::> controller_0423.supply to sink ::> controller_0424.power;
        interface link_0424_0425 : Common::PowerLink connect
            source ::> controller_0424.supply to sink ::> controller_0425.power;
        interface link_0425_0426 : Common::PowerLink connect
            source ::> controller_0425.supply to sink ::> controller_0426.power;
        interface link_0426_0427 : Common::PowerLink connect
            source ::> controller_0426.supply to sink ::> controller_0427.power;
        interface link_0427_0428 : Common::PowerLink connect
            source ::> controller_0427.supply to sink ::> controller_0428.power;
        interface link_0428_0429 : Common::PowerLink connect
            source ::> controller_0428.supply to sink ::> controller_0429.power;
        interface link_0429_0430 : Common::PowerLink connect
            source ::> controller_0429.supply to sink ::> controller_0430.power;
        interface link_0430_0431 : Common::PowerLink connect
            source ::> controller_0430.supply to sink ::> controller_0431.power;
        interface link_0431_0432 : Common::PowerLink connect
            source ::> controller_0431.supply to sink ::> controller_0432.power;
        interface link_0432_0433 : Common::PowerLink connect
            source ::> controller_0432.supply to sink ::> controller_0433.power;
        interface link_0433_0434 : Common::PowerLink connect
            source ::> controller_0433.supply to sink ::> controller_0434.power;
        interface link_0434_0435 : Common::PowerLink connect
            source ::> controller_0434.supply to sink ::> controller_0435.power;
        interface link_0435_0436 : Common::PowerLink connect
            source ::> controller_0435.supply to sink ::> controller_0436.power;
        interface link_0436_0437 : Common::PowerLink connect
            source ::> controller_0436.supply to sink ::> controller_0437.power;
        interface link_0437_0438 : Common::PowerLink connect
            source ::> controller_0437.supply to sink ::> controller_0438.power;
        interface link_0438_0439 : Common::PowerLink connect
            source ::> controller_0438.supply to sink ::> controller_0439.power;
        interface link_0439_0440 : Common::PowerLink connect
            source ::> controller_0439.supply to sink ::> controller_0440.power;
        interface link_0440_0441 : Common::PowerLink connect
            source ::> controller_0440.supply to sink ::> controller_0441.power;
        interface link_0441_0442 : Common::PowerLink connect
            source ::> controller_0441.supply to sink ::> controller_0442.power;
        interface link_0442_0443 : Common::PowerLink connect
            source ::> controller_0442.supply to sink ::> controller_0443.power;
        interface link_0443_0444 : Common::PowerLink connect
            source ::> controller_0443.supply to sink ::> controller_0444.power;
        interface link_0444_0445 : Common::PowerLink connect
            source ::> controller_0444.supply to sink ::> controller_0445.power;
        interface link_0445_0446 : Common::PowerLink connect
            source ::> controller_0445.supply to sink ::> controller_0446.power;
        interface link_0446_0447 : Common::PowerLink connect
            source ::> controller_0446.supply to sink ::> controller_0447.power;
        interface link_0447_0448 : Common::PowerLink connect
            source ::> controller_0447.supply to sink ::> controller_0448.power;
        interface link_0448_0449 : Common::PowerLink connect
            source ::> controller_0448.supply to sink ::> controller_0449.power;
        interface link_0449_0450 : Common::PowerLink connect
            source ::> controller_0449.supply to sink ::> controller_0450.power;
        interface link_0450_0451 : Common::PowerLink connect
            source ::> controller_0450.supply to sink ::> controller_0451.power;
        interface link_0451_0452 : Common::PowerLink connect
            source ::> controller_0451.supply to sink ::> controller_0452.power;
        interface link_0452_0453 : Common::PowerLink connect
            source ::> controller_0452.supply to sink ::> controller_0453.power;
        interface link_0453_0454 : Common::PowerLink connect
            source ::> controller_0453.supply to sink ::> controller_0454.power;
        interface link_0454_0455 : Common::PowerLink connect
            source ::> controller_0454.supply to sink ::> controller_0455.power;
        interface link_0455_0456 : Common::PowerLink connect
            source ::> controller_0455.supply to sink ::> controller_0456.power;
        interface link_0456_0457 : Common::PowerLink connect
            source ::> controller_0456.supply to sink ::> controller_0457.power;
        interface link_0457_0458 : Common::PowerLink connect
            source ::> controller_0457.supply to sink ::> controller_0458.power;
        interface link_0458_0459 : Common::PowerLink connect
            source ::> controller_0458.supply to sink ::> controller_0459.power;
        interface link_0459_0460 : Common::PowerLink connect
            source ::> controller_0459.supply to sink ::> controller_0460.power;
        interface link_0460_0461 : Common::PowerLink connect
            source ::> controller_0460.supply to sink ::> controller_0461.power;
        interface link_0461_0462 : Common::PowerLink connect
            source ::> controller_0461.supply to sink ::> controller_0462.power;
        interface link_0462_0463 : Common::PowerLink connect
            source ::> controller_0462.supply to sink ::> controller_0463.power;
        interface link_0463_0464 : Common::PowerLink connect
            source ::> controller_0463.supply to sink ::> controller_0464.power;
        interface link_0464_0465 : Common::PowerLink connect
            source ::> controller_0464.supply to sink ::> controller_0465.power;
        interface link_0465_0466 : Common::PowerLink connect
            source ::> controller_0465.supply to sink ::> controller_0466.power;
        interface link_0466_0467 : Common::PowerLink connect
            source ::> controller_0466.supply to sink ::> controller_0467.power;
        interface link_0467_0468 : Common::PowerLink connect
            source ::> controller_0467.supply to sink ::> controller_0468.power;
        interface link_0468_0469 : Common::PowerLink connect
            source ::> controller_0468.supply to sink ::> controller_0469.power;
        interface link_0469_0470 : Common::PowerLink connect
            source ::> controller_0469.supply to sink ::> controller_0470.power;
        interface link_0470_0471 : Common::PowerLink connect
            source ::> controller_0470.supply to sink ::> controller_0471.power;
        interface link_0471_0472 : Common::PowerLink connect
            source ::> controller_0471.supply to sink ::> controller_0472.power;
        interface link_0472_0473 : Common::PowerLink connect
            source ::> controller_0472.supply to sink ::> controller_0473.power;
        interface link_0473_0474 : Common::PowerLink connect
            source ::> controller_0473.supply to sink ::> controller_0474.power;
        interface link_0474_0475 : Common::PowerLink connect
            source ::> controller_0474.supply to sink ::> controller_0475.power;
        interface link_0475_0476 : Common::PowerLink connect
            source ::> controller_0475.supply to sink ::> controller_0476.power;
        interface link_0476_0477 : Common::PowerLink connect
            source ::> controller_0476.supply to sink ::> controller_0477.power;
        interface link_0477_0478 : Common::PowerLink connect
            source ::> controller_0477.supply to sink ::> controller_0478.power;
        interface link_0478_0479 : Common::PowerLink connect
            source ::> controller_0478.supply to sink ::> controller_0479.power;
        interface link_0479_0480 : Common::PowerLink connect
            source ::> controller_0479.supply to sink ::> controller_0480.power;
        interface link_0480_0481 : Common::PowerLink connect
            source ::> controller_0480.supply to sink ::> controller_0481.power;
        interface link_0481_0482 : Common::PowerLink connect
            source ::> controller_0481.supply to sink ::> controller_0482.power;
        interface link_0482_0483 : Common::PowerLink connect
            source ::> controller_0482.supply to sink ::> controller_0483.power;
        interface link_0483_0484 : Common::PowerLink connect
            source ::> controller_0483.supply to sink ::> controller_0484.power;
        interface link_0484_0485 : Common::PowerLink connect
            source ::> controller_0484.supply to sink ::> controller_0485.power;
        interface link_0485_0486 : Common::PowerLink connect
            source ::> controller_0485.supply to sink ::> controller_0486.power;
        interface link_0486_0487 : Common::PowerLink connect
            source ::> controller_0486.supply to sink ::> controller_0487.power;
        interface link_0487_0488 : Common::PowerLink connect
            source ::> controller_0487.supply to sink ::> controller_0488.power;
        interface link_0488_0489 : Common::PowerLink connect
            source ::> controller_0488.supply to sink ::> controller_0489.power;
        interface link_0489_0490 : Common::PowerLink connect
            source ::> controller_0489.supply to sink ::> controller_0490.power;
        interface link_0490_0491 : Common::PowerLink connect
            source ::> controller_0490.supply to sink ::> controller_0491.power;
        interface link_0491_0492 : Common::PowerLink connect
            source ::> controller_0491.supply to sink ::> controller_0492.power;
        interface link_0492_0493 : Common::PowerLink connect
            source ::> controller_0492.supply to sink ::> controller_0493.power;
        interface link_0493_0494 : Common::PowerLink connect
            source ::> controller_0493.supply to sink ::> controller_0494.power;
        interface link_0494_0495 : Common::PowerLink connect
            source ::> controller_0494.supply to sink ::> controller_0495.power;
        interface link_0495_0496 : Common::PowerLink connect
            source ::> controller_0495.supply to sink ::> controller_0496.power;
        interface link_0496_0497 : Common::PowerLink connect
            source ::> controller_0496.supply to sink ::> controller_0497.power;
        interface link_0497_0498 : Common::PowerLink connect
            source ::> controller_0497.supply to sink ::> controller_0498.power;
        interface link_0498_0499 : Common::PowerLink connect
            source ::> controller_0498.supply to sink ::> controller_0499.power;
        interface link_0499_0500 : Common::PowerLink connect
            source ::> controller_0499.supply to sink ::> controller_0500.power;
        interface link_0500_0501 : Common::PowerLink connect
            source ::> controller_0500.supply to sink ::> controller_0501.power;
        interface link_0501_0502 : Common::PowerLink connect
            source ::> controller_0501.supply to sink ::> controller_0502.power;
        interface link_0502_0503 : Common::PowerLink connect
            source ::> controller_0502.supply to sink ::> controller_0503.power;
        interface link_0503_0504 : Common::PowerLink connect
            source ::> controller_0503.supply to sink ::> controller_0504.power;
        interface link_0504_0505 : Common::PowerLink connect
            source ::> controller_0504.supply to sink ::> controller_0505.power;
        interface link_0505_0506 : Common::PowerLink connect
            source ::> controller_0505.supply to sink ::> controller_0506.power;
        interface link_0506_0507 : Common::PowerLink connect
            source ::> controller_0506.supply to sink ::> controller_0507.power;
        interface link_0507_0508 : Common::PowerLink connect
            source ::> controller_0507.supply to sink ::> controller_0508.power;
        interface link_0508_0509 : Common::PowerLink connect
            source ::> controller_0508.supply to sink ::> controller_0509.power;
        interface link_0509_0510 : Common::PowerLink connect
            source ::> controller_0509.supply to sink ::> controller_0510.power;
        interface link_0510_0511 : Common::PowerLink connect
            source ::> controller_0510.supply to sink ::> controller_0511.power;
        interface link_0511_0512 : Common::PowerLink connect
            source ::> controller_0511.supply to sink ::> controller_0512.power;
        interface link_0512_0513 : Common::PowerLink connect
            source ::> controller_0512.supply to sink ::> controller_0513.power;
        interface link_0513_0514 : Common::PowerLink connect
            source ::> controller_0513.supply to sink ::> controller_0514.power;
        interface link_0514_0515 : Common::PowerLink connect
            source ::> controller_0514.supply to sink ::> controller_0515.power;
        interface link_0515_0516 : Common::PowerLink connect
            source ::> controller_0515.supply to sink ::> controller_0516.power;
        interface link_0516_0517 : Common::PowerLink connect
            source ::> controller_0516.supply to sink ::> controller_0517.power;
        interface link_0517_0518 : Common::PowerLink connect
            source ::> controller_0517.supply to sink ::> controller_0518.power;
        interface link_0518_0519 : Common::PowerLink connect
            source ::> controller_0518.supply to sink ::> controller_0519.power;
        interface link_0519_0520 : Common::PowerLink connect
            source ::> controller_0519.supply to sink ::> controller_0520.power;
        interface link_0520_0521 : Common::PowerLink connect
            source ::> controller_0520.supply to sink ::> controller_0521.power;
        interface link_0521_0522 : Common::PowerLink connect
            source ::> controller_0521.supply to sink ::> controller_0522.power;
        interface link_0522_0523 : Common::PowerLink connect
            source ::> controller_0522.supply to sink ::> controller_0523.power;
        interface link_0523_0524 : Common::PowerLink connect
            source ::> controller_0523.supply to sink ::> controller_0524.power;
        interface link_0524_0525 : Common::PowerLink connect
            source ::> controller_0524.supply to sink ::> controller_0525.power;
        interface link_0525_0526 : Common::PowerLink connect
            source ::> controller_0525.supply to sink ::> controller_0526.power;
        interface link_0526_0527 : Common::PowerLink connect
            source ::> controller_0526.supply to sink ::> controller_0527.power;
        interface link_0527_0528 : Common::PowerLink connect
            source ::> controller_0527.supply to sink ::> controller_0528.power;
        interface link_0528_0529 : Common::PowerLink connect
            source ::> controller_0528.supply to sink ::> controller_0529.power;
        interface link_0529_0530 : Common::PowerLink connect
            source ::> controller_0529.supply to sink ::> controller_0530.power;
        interface link_0530_0531 : Common::PowerLink connect
            source ::> controller_0530.supply to sink ::> controller_0531.power;
        interface link_0531_0532 : Common::PowerLink connect
            source ::> controller_0531.supply to sink ::> controller_0532.power;
        interface link_0532_0533 : Common::PowerLink connect
            source ::> controller_0532.supply to sink ::> controller_0533.power;
        interface link_0533_0534 : Common::PowerLink connect
            source ::> controller_0533.supply to sink ::> controller_0534.power;
        interface link_0534_0535 : Common::PowerLink connect
            source ::> controller_0534.supply to sink ::> controller_0535.power;
        interface link_0535_0536 : Common::PowerLink connect
            source ::> controller_0535.supply to sink ::> controller_0536.power;
        interface link_0536_0537 : Common::PowerLink connect
            source ::> controller_0536.supply to sink ::> controller_0537.power;
        interface link_0537_0538 : Common::PowerLink connect
            source ::> controller_0537.supply to sink ::> controller_0538.power;
        interface link_0538_0539 : Common::PowerLink connect
            source ::> controller_0538.supply to sink ::> controller_0539.power;
        interface link_0539_0540 : Common::PowerLink connect
            source ::> controller_0539.supply to sink ::> controller_0540.power;
        interface link_0540_0541 : Common::PowerLink connect
            source ::> controller_0540.supply to sink ::> controller_0541.power;
        interface link_0541_0542 : Common::PowerLink connect
            source ::> controller_0541.supply to sink ::> controller_0542.power;
        interface link_0542_0543 : Common::PowerLink connect
            source ::> controller_0542.supply to sink ::> controller_0543.power;
        interface link_0543_0544 : Common::PowerLink connect
            source ::> controller_0543.supply to sink ::> controller_0544.power;
        interface link_0544_0545 : Common::PowerLink connect
            source ::> controller_0544.supply to sink ::> controller_0545.power;
        interface link_0545_0546 : Common::PowerLink connect
            source ::> controller_0545.supply to sink ::> controller_0546.power;
        interface link_0546_0547 : Common::PowerLink connect
            source ::> controller_0546.supply to sink ::> controller_0547.power;
        interface link_0547_0548 : Common::PowerLink connect
            source ::> controller_0547.supply to sink ::> controller_0548.power;
        interface link_0548_0549 : Common::PowerLink connect
            source ::> controller_0548.supply to sink ::> controller_0549.power;
        interface link_0549_0550 : Common::PowerLink connect
            source ::> controller_0549.supply to sink ::> controller_0550.power;
        interface link_0550_0551 : Common::PowerLink connect
            source ::> controller_0550.supply to sink ::> controller_0551.power;
        interface link_0551_0552 : Common::PowerLink connect
            source ::> controller_0551.supply to sink ::> controller_0552.power;
        interface link_0552_0553 : Common::PowerLink connect
            source ::> controller_0552.supply to sink ::> controller_0553.power;
        interface link_0553_0554 : Common::PowerLink connect
            source ::> controller_0553.supply to sink ::> controller_0554.power;
        interface link_0554_0555 : Common::PowerLink connect
            source ::> controller_0554.supply to sink ::> controller_0555.power;
        interface link_0555_0556 : Common::PowerLink connect
            source ::> controller_0555.supply to sink ::> controller_0556.power;
        interface link_0556_0557 : Common::PowerLink connect
            source ::> controller_0556.supply to sink ::> controller_0557.power;
        interface link_0557_0558 : Common::PowerLink connect
            source ::> controller_0557.supply to sink ::> controller_0558.power;
        interface link_0558_0559 : Common::PowerLink connect
            source ::> controller_0558.supply to sink ::> controller_0559.power;
        interface link_0559_0560 : Common::PowerLink connect
            source ::> controller_0559.supply to sink ::> controller_0560.power;
        interface link_0560_0561 : Common::PowerLink connect
            source ::> controller_0560.supply to sink ::> controller_0561.power;
        interface link_0561_0562 : Common::PowerLink connect
            source ::> controller_0561.supply to sink ::> controller_0562.power;
        interface link_0562_0563 : Common::PowerLink connect
            source ::> controller_0562.supply to sink ::> controller_0563.power;
        interface link_0563_0564 : Common::PowerLink connect
            source ::> controller_0563.supply to sink ::> controller_0564.power;
        interface link_0564_0565 : Common::PowerLink connect
            source ::> controller_0564.supply to sink ::> controller_0565.power;
        interface link_0565_0566 : Common::PowerLink connect
            source ::> controller_0565.supply to sink ::> controller_0566.power;
        interface link_0566_0567 : Common::PowerLink connect
            source ::> controller_0566.supply to sink ::> controller_0567.power;
        interface link_0567_0568 : Common::PowerLink connect
            source ::> controller_0567.supply to sink ::> controller_0568.power;
        interface link_0568_0569 : Common::PowerLink connect
            source ::> controller_0568.supply to sink ::> controller_0569.power;
        interface link_0569_0570 : Common::PowerLink connect
            source ::> controller_0569.supply to sink ::> controller_0570.power;
        interface link_0570_0571 : Common::PowerLink connect
            source ::> controller_0570.supply to sink ::> controller_0571.power;
        interface link_0571_0572 : Common::PowerLink connect
            source ::> controller_0571.supply to sink ::> controller_0572.power;
        interface link_0572_0573 : Common::PowerLink connect
            source ::> controller_0572.supply to sink ::> controller_0573.power;
        interface link_0573_0574 : Common::PowerLink connect
            source ::> controller_0573.supply to sink ::> controller_0574.power;
        interface link_0574_0575 : Common::PowerLink connect
            source ::> controller_0574.supply to sink ::> controller_0575.power;
        interface link_0575_0576 : Common::PowerLink connect
            source ::> controller_0575.supply to sink ::> controller_0576.power;
        interface link_0576_0577 : Common::PowerLink connect
            source ::> controller_0576.supply to sink ::> controller_0577.power;
        interface link_0577_0578 : Common::PowerLink connect
            source ::> controller_0577.supply to sink ::> controller_0578.power;
        interface link_0578_0579 : Common::PowerLink connect
            source ::> controller_0578.supply to sink ::> controller_0579.power;
        interface link_0579_0580 : Common::PowerLink connect
            source ::> controller_0579.supply to sink ::> controller_0580.power;
        interface link_0580_0581 : Common::PowerLink connect
            source ::> controller_0580.supply to sink ::> controller_0581.power;
        interface link_0581_0582 : Common::PowerLink connect
            source ::> controller_0581.supply to sink ::> controller_0582.power;
        interface link_0582_0583 : Common::PowerLink connect
            source ::> controller_0582.supply to sink ::> controller_0583.power;
        interface link_0583_0584 : Common::PowerLink connect
            source ::> controller_0583.supply to sink ::> controller_0584.power;
        interface link_0584_0585 : Common::PowerLink connect
            source ::> controller_0584.supply to sink ::> controller_0585.power;
        interface link_0585_0586 : Common::PowerLink connect
            source ::> controller_0585.supply to sink ::> controller_0586.power;
        interface link_0586_0587 : Common::PowerLink connect
            source ::> controller_0586.supply to sink ::> controller_0587.power;
        interface link_0587_0588 : Common::PowerLink connect
            source ::> controller_0587.supply to sink ::> controller_0588.power;
        interface link_0588_0589 : Common::PowerLink connect
            source ::> controller_0588.supply to sink ::> controller_0589.power;
        interface link_0589_0590 : Common::PowerLink connect
            source ::> controller_0589.supply to sink ::> controller_0590.power;
        interface link_0590_0591 : Common::PowerLink connect
            source ::> controller_0590.supply to sink ::> controller_0591.power;
        interface link_0591_0592 : Common::PowerLink connect
            source ::> controller_0591.supply to sink ::> controller_0592.power;
        interface link_0592_0593 : Common::PowerLink connect
            source ::> controller_0592.supply to sink ::> controller_0593.power;
        interface link_0593_0594 : Common::PowerLink connect
            source ::> controller_0593.supply to sink ::> controller_0594.power;
        interface link_0594_0595 : Common::PowerLink connect
            source ::> controller_0594.supply to sink ::> controller_0595.power;
        interface link_0595_0596 : Common::PowerLink connect
            source ::> controller_0595.supply to sink ::> controller_0596.power;
        interface link_0596_0597 : Common::PowerLink connect
            source ::> controller_0596.supply to sink ::> controller_0597.power;
        interface link_0597_0598 : Common::PowerLink connect
            source ::> controller_0597.supply to sink ::> controller_0598.power;
        interface link_0598_0599 : Common::PowerLink connect
            source ::> controller_0598.supply to sink ::> controller_0599.power;
        interface link_0599_0600 : Common::PowerLink connect
            source ::> controller_0599.supply to sink ::> controller_0600.power;
        interface link_0600_0601 : Common::PowerLink connect
            source ::> controller_0600.supply to sink ::> controller_0601.power;
        interface link_0601_0602 : Common::PowerLink connect
            source ::> controller_0601.supply to sink ::> controller_0602.power;
        interface link_0602_0603 : Common::PowerLink connect
            source ::> controller_0602.supply to sink ::> controller_0603.power;
        interface link_0603_0604 : Common::PowerLink connect
            source ::> controller_0603.supply to sink ::> controller_0604.power;
        interface link_0604_0605 : Common::PowerLink connect
            source ::> controller_0604.supply to sink ::> controller_0605.power;
        interface link_0605_0606 : Common::PowerLink connect
            source ::> controller_0605.supply to sink ::> controller_0606.power;
        interface link_0606_0607 : Common::PowerLink connect
            source ::> controller_0606.supply to sink ::> controller_0607.power;
        interface link_0607_0608 : Common::PowerLink connect
            source ::> controller_0607.supply to sink ::> controller_0608.power;
        interface link_0608_0609 : Common::PowerLink connect
            source ::> controller_0608.supply to sink ::> controller_0609.power;
        interface link_0609_0610 : Common::PowerLink connect
            source ::> controller_0609.supply to sink ::> controller_0610.power;
        interface link_0610_0611 : Common::PowerLink connect
            source ::> controller_0610.supply to sink ::> controller_0611.power;
        interface link_0611_0612 : Common::PowerLink connect
            source ::> controller_0611.supply to sink ::> controller_0612.power;
        interface link_0612_0613 : Common::PowerLink connect
            source ::> controller_0612.supply to sink ::> controller_0613.power;
        interface link_0613_0614 : Common::PowerLink connect
            source ::> controller_0613.supply to sink ::> controller_0614.power;
        interface link_0614_0615 : Common::PowerLink connect
            source ::> controller_0614.supply to sink ::> controller_0615.power;
        interface link_0615_0616 : Common::PowerLink connect
            source ::> controller_0615.supply to sink ::> controller_0616.power;
        interface link_0616_0617 : Common::PowerLink connect
            source ::> controller_0616.supply to sink ::> controller_0617.power;
        interface link_0617_0618 : Common::PowerLink connect
            source ::> controller_0617.supply to sink ::> controller_0618.power;
        interface link_0618_0619 : Common::PowerLink connect
            source ::> controller_0618.supply to sink ::> controller_0619.power;
        interface link_0619_0620 : Common::PowerLink connect
            source ::> controller_0619.supply to sink ::> controller_0620.power;
        interface link_0620_0621 : Common::PowerLink connect
            source ::> controller_0620.supply to sink ::> controller_0621.power;
        interface link_0621_0622 : Common::PowerLink connect
            source ::> controller_0621.supply to sink ::> controller_0622.power;
        interface link_0622_0623 : Common::PowerLink connect
            source ::> controller_0622.supply to sink ::> controller_0623.power;
        interface link_0623_0624 : Common::PowerLink connect
            source ::> controller_0623.supply to sink ::> controller_0624.power;
        interface link_0624_0625 : Common::PowerLink connect
            source ::> controller_0624.supply to sink ::> controller_0625.power;
        interface link_0625_0626 : Common::PowerLink connect
            source ::> controller_0625.supply to sink ::> controller_0626.power;
        interface link_0626_0627 : Common::PowerLink connect
            source ::> controller_0626.supply to sink ::> controller_0627.power;
        interface link_0627_0628 : Common::PowerLink connect
            source ::> controller_0627.supply to sink ::> controller_0628.power;
        interface link_0628_0629 : Common::PowerLink connect
            source ::> controller_0628.supply to sink ::> controller_0629.power;
        interface link_0629_0630 : Common::PowerLink connect
            source ::> controller_0629.supply to sink ::> controller_0630.power;
        interface link_0630_0631 : Common::PowerLink connect
            source ::> controller_0630.supply to sink ::> controller_0631.power;
        interface link_0631_0632 : Common::PowerLink connect
            source ::> controller_0631.supply to sink ::> controller_0632.power;
        interface link_0632_0633 : Common::PowerLink connect
            source ::> controller_0632.supply to sink ::> controller_0633.power;
        interface link_0633_0634 : Common::PowerLink connect
            source ::> controller_0633.supply to sink ::> controller_0634.power;
        interface link_0634_0635 : Common::PowerLink connect
            source ::> controller_0634.supply to sink ::> controller_0635.power;
        interface link_0635_0636 : Common::PowerLink connect
            source ::> controller_0635.supply to sink ::> controller_0636.power;
        interface link_0636_0637 : Common::PowerLink connect
            source ::> controller_0636.supply to sink ::> controller_0637.power;
        interface link_0637_0638 : Common::PowerLink connect
            source ::> controller_0637.supply to sink ::> controller_0638.power;
        interface link_0638_0639 : Common::PowerLink connect
            source ::> controller_0638.supply to sink ::> controller_0639.power;
        interface link_0639_0640 : Common::PowerLink connect
            source ::> controller_0639.supply to sink ::> controller_0640.power;
        interface link_0640_0641 : Common::PowerLink connect
            source ::> controller_0640.supply to sink ::> controller_0641.power;
        interface link_0641_0642 : Common::PowerLink connect
            source ::> controller_0641.supply to sink ::> controller_0642.power;
        interface link_0642_0643 : Common::PowerLink connect
            source ::> controller_0642.supply to sink ::> controller_0643.power;
        interface link_0643_0644 : Common::PowerLink connect
            source ::> controller_0643.supply to sink ::> controller_0644.power;
        interface link_0644_0645 : Common::PowerLink connect
            source ::> controller_0644.supply to sink ::> controller_0645.power;
        interface link_0645_0646 : Common::PowerLink connect
            source ::> controller_0645.supply to sink ::> controller_0646.power;
        interface link_0646_0647 : Common::PowerLink connect
            source ::> controller_0646.supply to sink ::> controller_0647.power;
        interface link_0647_0648 : Common::PowerLink connect
            source ::> controller_0647.supply to sink ::> controller_0648.power;
        interface link_0648_0649 : Common::PowerLink connect
            source ::> controller_0648.supply to sink ::> controller_0649.power;
        interface link_0649_0650 : Common::PowerLink connect
            source ::> controller_0649.supply to sink ::> controller_0650.power;
        interface link_0650_0651 : Common::PowerLink connect
            source ::> controller_0650.supply to sink ::> controller_0651.power;
        interface link_0651_0652 : Common::PowerLink connect
            source ::> controller_0651.supply to sink ::> controller_0652.power;
        interface link_0652_0653 : Common::PowerLink connect
            source ::> controller_0652.supply to sink ::> controller_0653.power;
        interface link_0653_0654 : Common::PowerLink connect
            source ::> controller_0653.supply to sink ::> controller_0654.power;
        interface link_0654_0655 : Common::PowerLink connect
            source ::> controller_0654.supply to sink ::> controller_0655.power;
        interface link_0655_0656 : Common::PowerLink connect
            source ::> controller_0655.supply to sink ::> controller_0656.power;
        interface link_0656_0657 : Common::PowerLink connect
            source ::> controller_0656.supply to sink ::> controller_0657.power;
        interface link_0657_0658 : Common::PowerLink connect
            source ::> controller_0657.supply to sink ::> controller_0658.power;
        interface link_0658_0659 : Common::PowerLink connect
            source ::> controller_0658.supply to sink ::> controller_0659.power;
        interface link_0659_0660 : Common::PowerLink connect
            source ::> controller_0659.supply to sink ::> controller_0660.power;
        interface link_0660_0661 : Common::PowerLink connect
            source ::> controller_0660.supply to sink ::> controller_0661.power;
        interface link_0661_0662 : Common::PowerLink connect
            source ::> controller_0661.supply to sink ::> controller_0662.power;
        interface link_0662_0663 : Common::PowerLink connect
            source ::> controller_0662.supply to sink ::> controller_0663.power;
        interface link_0663_0664 : Common::PowerLink connect
            source ::> controller_0663.supply to sink ::> controller_0664.power;
        interface link_0664_0665 : Common::PowerLink connect
            source ::> controller_0664.supply to sink ::> controller_0665.power;
        interface link_0665_0666 : Common::PowerLink connect
            source ::> controller_0665.supply to sink ::> controller_0666.power;
        interface link_0666_0667 : Common::PowerLink connect
            source ::> controller_0666.supply to sink ::> controller_0667.power;
        interface link_0667_0668 : Common::PowerLink connect
            source ::> controller_0667.supply to sink ::> controller_0668.power;
        interface link_0668_0669 : Common::PowerLink connect
            source ::> controller_0668.supply to sink ::> controller_0669.power;
        interface link_0669_0670 : Common::PowerLink connect
            source ::> controller_0669.supply to sink ::> controller_0670.power;
        interface link_0670_0671 : Common::PowerLink connect
            source ::> controller_0670.supply to sink ::> controller_0671.power;
        interface link_0671_0672 : Common::PowerLink connect
            source ::> controller_0671.supply to sink ::> controller_0672.power;
        interface link_0672_0673 : Common::PowerLink connect
            source ::> controller_0672.supply to sink ::> controller_0673.power;
        interface link_0673_0674 : Common::PowerLink connect
            source ::> controller_0673.supply to sink ::> controller_0674.power;
        interface link_0674_0675 : Common::PowerLink connect
            source ::> controller_0674.supply to sink ::> controller_0675.power;
        interface link_0675_0676 : Common::PowerLink connect
            source ::> controller_0675.supply to sink ::> controller_0676.power;
        interface link_0676_0677 : Common::PowerLink connect
            source ::> controller_0676.supply to sink ::> controller_0677.power;
        interface link_0677_0678 : Common::PowerLink connect
            source ::> controller_0677.supply to sink ::> controller_0678.power;
        interface link_0678_0679 : Common::PowerLink connect
            source ::> controller_0678.supply to sink ::> controller_0679.power;
        interface link_0679_0680 : Common::PowerLink connect
            source ::> controller_0679.supply to sink ::> controller_0680.power;
        interface link_0680_0681 : Common::PowerLink connect
            source ::> controller_0680.supply to sink ::> controller_0681.power;
        interface link_0681_0682 : Common::PowerLink connect
            source ::> controller_0681.supply to sink ::> controller_0682.power;
        interface link_0682_0683 : Common::PowerLink connect
            source ::> controller_0682.supply to sink ::> controller_0683.power;
        interface link_0683_0684 : Common::PowerLink connect
            source ::> controller_0683.supply to sink ::> controller_0684.power;
        interface link_0684_0685 : Common::PowerLink connect
            source ::> controller_0684.supply to sink ::> controller_0685.power;
        interface link_0685_0686 : Common::PowerLink connect
            source ::> controller_0685.supply to sink ::> controller_0686.power;
        interface link_0686_0687 : Common::PowerLink connect
            source ::> controller_0686.supply to sink ::> controller_0687.power;
        interface link_0687_0688 : Common::PowerLink connect
            source ::> controller_0687.supply to sink ::> controller_0688.power;
        interface link_0688_0689 : Common::PowerLink connect
            source ::> controller_0688.supply to sink ::> controller_0689.power;
        interface link_0689_0690 : Common::PowerLink connect
            source ::> controller_0689.supply to sink ::> controller_0690.power;
        interface link_0690_0691 : Common::PowerLink connect
            source ::> controller_0690.supply to sink ::> controller_0691.power;
        interface link_0691_0692 : Common::PowerLink connect
            source ::> controller_0691.supply to sink ::> controller_0692.power;
        interface link_0692_0693 : Common::PowerLink connect
            source ::> controller_0692.supply to sink ::> controller_0693.power;
        interface link_0693_0694 : Common::PowerLink connect
            source ::> controller_0693.supply to sink ::> controller_0694.power;
        interface link_0694_0695 : Common::PowerLink connect
            source ::> controller_0694.supply to sink ::> controller_0695.power;
        interface link_0695_0696 : Common::PowerLink connect
            source ::> controller_0695.supply to sink ::> controller_0696.power;
        interface link_0696_0697 : Common::PowerLink connect
            source ::> controller_0696.supply to sink ::> controller_0697.power;
        interface link_0697_0698 : Common::PowerLink connect
            source ::> controller_0697.supply to sink ::> controller_0698.power;
        interface link_0698_0699 : Common::PowerLink connect
            source ::> controller_0698.supply to sink ::> controller_0699.power;
        interface link_0699_0700 : Common::PowerLink connect
            source ::> controller_0699.supply to sink ::> controller_0700.power;
        interface link_0700_0701 : Common::PowerLink connect
            source ::> controller_0700.supply to sink ::> controller_0701.power;
        interface link_0701_0702 : Common::PowerLink connect
            source ::> controller_0701.supply to sink ::> controller_0702.power;
        interface link_0702_0703 : Common::PowerLink connect
            source ::> controller_0702.supply to sink ::> controller_0703.power;
        interface link_0703_0704 : Common::PowerLink connect
            source ::> controller_0703.supply to sink ::> controller_0704.power;
        interface link_0704_0705 : Common::PowerLink connect
            source ::> controller_0704.supply to sink ::> controller_0705.power;
        interface link_0705_0706 : Common::PowerLink connect
            source ::> controller_0705.supply to sink ::> controller_0706.power;
        interface link_0706_0707 : Common::PowerLink connect
            source ::> controller_0706.supply to sink ::> controller_0707.power;
        interface link_0707_0708 : Common::PowerLink connect
            source ::> controller_0707.supply to sink ::> controller_0708.power;
        interface link_0708_0709 : Common::PowerLink connect
            source ::> controller_0708.supply to sink ::> controller_0709.power;
        interface link_0709_0710 : Common::PowerLink connect
            source ::> controller_0709.supply to sink ::> controller_0710.power;
        interface link_0710_0711 : Common::PowerLink connect
            source ::> controller_0710.supply to sink ::> controller_0711.power;
        interface link_0711_0712 : Common::PowerLink connect
            source ::> controller_0711.supply to sink ::> controller_0712.power;
        interface link_0712_0713 : Common::PowerLink connect
            source ::> controller_0712.supply to sink ::> controller_0713.power;
        interface link_0713_0714 : Common::PowerLink connect
            source ::> controller_0713.supply to sink ::> controller_0714.power;
        interface link_0714_0715 : Common::PowerLink connect
            source ::> controller_0714.supply to sink ::> controller_0715.power;
        interface link_0715_0716 : Common::PowerLink connect
            source ::> controller_0715.supply to sink ::> controller_0716.power;
        interface link_0716_0717 : Common::PowerLink connect
            source ::> controller_0716.supply to sink ::> controller_0717.power;
        interface link_0717_0718 : Common::PowerLink connect
            source ::> controller_0717.supply to sink ::> controller_0718.power;
        interface link_0718_0719 : Common::PowerLink connect
            source ::> controller_0718.supply to sink ::> controller_0719.power;
        interface link_0719_0720 : Common::PowerLink connect
            source ::> controller_0719.supply to sink ::> controller_0720.power;
        interface link_0720_0721 : Common::PowerLink connect
            source ::> controller_0720.supply to sink ::> controller_0721.power;
        interface link_0721_0722 : Common::PowerLink connect
            source ::> controller_0721.supply to sink ::> controller_0722.power;
        interface link_0722_0723 : Common::PowerLink connect
            source ::> controller_0722.supply to sink ::> controller_0723.power;
        interface link_0723_0724 : Common::PowerLink connect
            source ::> controller_0723.supply to sink ::> controller_0724.power;
        interface link_0724_0725 : Common::PowerLink connect
            source ::> controller_0724.supply to sink ::> controller_0725.power;
        interface link_0725_0726 : Common::PowerLink connect
            source ::> controller_0725.supply to sink ::> controller_0726.power;
        interface link_0726_0727 : Common::PowerLink connect
            source ::> controller_0726.supply to sink ::> controller_0727.power;
        interface link_0727_0728 : Common::PowerLink connect
            source ::> controller_0727.supply to sink ::> controller_0728.power;
        interface link_0728_0729 : Common::PowerLink connect
            source ::> controller_0728.supply to sink ::> controller_0729.power;
        interface link_0729_0730 : Common::PowerLink connect
            source ::> controller_0729.supply to sink ::> controller_0730.power;
        interface link_0730_0731 : Common::PowerLink connect
            source ::> controller_0730.supply to sink ::> controller_0731.power;
        interface link_0731_0732 : Common::PowerLink connect
            source ::> controller_0731.supply to sink ::> controller_0732.power;
        interface link_0732_0733 : Common::PowerLink connect
            source ::> controller_0732.supply to sink ::> controller_0733.power;
        interface link_0733_0734 : Common::PowerLink connect
            source ::> controller_0733.supply to sink ::> controller_0734.power;
        interface link_0734_0735 : Common::PowerLink connect
            source ::> controller_0734.supply to sink ::> controller_0735.power;
        interface link_0735_0736 : Common::PowerLink connect
            source ::> controller_0735.supply to sink ::> controller_0736.power;
        interface link_0736_0737 : Common::PowerLink connect
            source ::> controller_0736.supply to sink ::> controller_0737.power;
        interface link_0737_0738 : Common::PowerLink connect
            source ::> controller_0737.supply to sink ::> controller_0738.power;
        interface link_0738_0739 : Common::PowerLink connect
            source ::> controller_0738.supply to sink ::> controller_0739.power;
        interface link_0739_0740 : Common::PowerLink connect
            source ::> controller_0739.supply to sink ::> controller_0740.power;
        interface link_0740_0741 : Common::PowerLink connect
            source ::> controller_0740.supply to sink ::> controller_0741.power;
        interface link_0741_0742 : Common::PowerLink connect
            source ::> controller_0741.supply to sink ::> controller_0742.power;
        interface link_0742_0743 : Common::PowerLink connect
            source ::> controller_0742.supply to sink ::> controller_0743.power;
        interface link_0743_0744 : Common::PowerLink connect
            source ::> controller_0743.supply to sink ::> controller_0744.power;
        interface link_0744_0745 : Common::PowerLink connect
            source ::> controller_0744.supply to sink ::> controller_0745.power;
        interface link_0745_0746 : Common::PowerLink connect
            source ::> controller_0745.supply to sink ::> controller_0746.power;
        interface link_0746_0747 : Common::PowerLink connect
            source ::> controller_0746.supply to sink ::> controller_0747.power;
        interface link_0747_0748 : Common::PowerLink connect
            source ::> controller_0747.supply to sink ::> controller_0748.power;
        interface link_0748_0749 : Common::PowerLink connect
            source ::> controller_0748.supply to sink ::> controller_0749.power;
        interface link_0749_0750 : Common::PowerLink connect
            source ::> controller_0749.supply to sink ::> controller_0750.power;
        interface link_0750_0751 : Common::PowerLink connect
            source ::> controller_0750.supply to sink ::> controller_0751.power;
        interface link_0751_0752 : Common::PowerLink connect
            source ::> controller_0751.supply to sink ::> controller_0752.power;
        interface link_0752_0753 : Common::PowerLink connect
            source ::> controller_0752.supply to sink ::> controller_0753.power;
        interface link_0753_0754 : Common::PowerLink connect
            source ::> controller_0753.supply to sink ::> controller_0754.power;
        interface link_0754_0755 : Common::PowerLink connect
            source ::> controller_0754.supply to sink ::> controller_0755.power;
        interface link_0755_0756 : Common::PowerLink connect
            source ::> controller_0755.supply to sink ::> controller_0756.power;
        interface link_0756_0757 : Common::PowerLink connect
            source ::> controller_0756.supply to sink ::> controller_0757.power;
        interface link_0757_0758 : Common::PowerLink connect
            source ::> controller_0757.supply to sink ::> controller_0758.power;
        interface link_0758_0759 : Common::PowerLink connect
            source ::> controller_0758.supply to sink ::> controller_0759.power;
        interface link_0759_0760 : Common::PowerLink connect
            source ::> controller_0759.supply to sink ::> controller_0760.power;
        interface link_0760_0761 : Common::PowerLink connect
            source ::> controller_0760.supply to sink ::> controller_0761.power;
        interface link_0761_0762 : Common::PowerLink connect
            source ::> controller_0761.supply to sink ::> controller_0762.power;
        interface link_0762_0763 : Common::PowerLink connect
            source ::> controller_0762.supply to sink ::> controller_0763.power;
        interface link_0763_0764 : Common::PowerLink connect
            source ::> controller_0763.supply to sink ::> controller_0764.power;
        interface link_0764_0765 : Common::PowerLink connect
            source ::> controller_0764.supply to sink ::> controller_0765.power;
        interface link_0765_0766 : Common::PowerLink connect
            source ::> controller_0765.supply to sink ::> controller_0766.power;
        interface link_0766_0767 : Common::PowerLink connect
            source ::> controller_0766.supply to sink ::> controller_0767.power;
        interface link_0767_0768 : Common::PowerLink connect
            source ::> controller_0767.supply to sink ::> controller_0768.power;
        interface link_0768_0769 : Common::PowerLink connect
            source ::> controller_0768.supply to sink ::> controller_0769.power;
        interface link_0769_0770 : Common::PowerLink connect
            source ::> controller_0769.supply to sink ::> controller_0770.power;
        interface link_0770_0771 : Common::PowerLink connect
            source ::> controller_0770.supply to sink ::> controller_0771.power;
        interface link_0771_0772 : Common::PowerLink connect
            source ::> controller_0771.supply to sink ::> controller_0772.power;
        interface link_0772_0773 : Common::PowerLink connect
            source ::> controller_0772.supply to sink ::> controller_0773.power;
        interface link_0773_0774 : Common::PowerLink connect
            source ::> controller_0773.supply to sink ::> controller_0774.power;
        interface link_0774_0775 : Common::PowerLink connect
            source ::> controller_0774.supply to sink ::> controller_0775.power;
        interface link_0775_0776 : Common::PowerLink connect
            source ::> controller_0775.supply to sink ::> controller_0776.power;
        interface link_0776_0777 : Common::PowerLink connect
            source ::> controller_0776.supply to sink ::> controller_0777.power;
        interface link_0777_0778 : Common::PowerLink connect
            source ::> controller_0777.supply to sink ::> controller_0778.power;
        interface link_0778_0779 : Common::PowerLink connect
            source ::> controller_0778.supply to sink ::> controller_0779.power;
        interface link_0779_0780 : Common::PowerLink connect
            source ::> controller_0779.supply to sink ::> controller_0780.power;
        interface link_0780_0781 : Common::PowerLink connect
            source ::> controller_0780.supply to sink ::> controller_0781.power;
        interface link_0781_0782 : Common::PowerLink connect
            source ::> controller_0781.supply to sink ::> controller_0782.power;
        interface link_0782_0783 : Common::PowerLink connect
            source ::> controller_0782.supply to sink ::> controller_0783.power;
        interface link_0783_0784 : Common::PowerLink connect
            source ::> controller_0783.supply to sink ::> controller_0784.power;
        interface link_0784_0785 : Common::PowerLink connect
            source ::> controller_0784.supply to sink ::> controller_0785.power;
        interface link_0785_0786 : Common::PowerLink connect
            source ::> controller_0785.supply to sink ::> controller_0786.power;
        interface link_0786_0787 : Common::PowerLink connect
            source ::> controller_0786.supply to sink ::> controller_0787.power;
        interface link_0787_0788 : Common::PowerLink connect
            source ::> controller_0787.supply to sink ::> controller_0788.power;
        interface link_0788_0789 : Common::PowerLink connect
            source ::> controller_0788.supply to sink ::> controller_0789.power;
        interface link_0789_0790 : Common::PowerLink connect
            source ::> controller_0789.supply to sink ::> controller_0790.power;
        interface link_0790_0791 : Common::PowerLink connect
            source ::> controller_0790.supply to sink ::> controller_0791.power;
        interface link_0791_0792 : Common::PowerLink connect
            source ::> controller_0791.supply to sink ::> controller_0792.power;
        interface link_0792_0793 : Common::PowerLink connect
            source ::> controller_0792.supply to sink ::> controller_0793.power;
        interface link_0793_0794 : Common::PowerLink connect
            source ::> controller_0793.supply to sink ::> controller_0794.power;
        interface link_0794_0795 : Common::PowerLink connect
            source ::> controller_0794.supply to sink ::> controller_0795.power;
        interface link_0795_0796 : Common::PowerLink connect
            source ::> controller_0795.supply to sink ::> controller_0796.power;
        interface link_0796_0797 : Common::PowerLink connect
            source ::> controller_0796.supply to sink ::> controller_0797.power;
        interface link_0797_0798 : Common::PowerLink connect
            source ::> controller_0797.supply to sink ::> controller_0798.power;
        interface link_0798_0799 : Common::PowerLink connect
            source ::> controller_0798.supply to sink ::> controller_0799.power;
        interface link_0799_0800 : Common::PowerLink connect
            source ::> controller_0799.supply to sink ::> controller_0800.power;
        interface link_0800_0801 : Common::PowerLink connect
            source ::> controller_0800.supply to sink ::> controller_0801.power;
        interface link_0801_0802 : Common::PowerLink connect
            source ::> controller_0801.supply to sink ::> controller_0802.power;
        interface link_0802_0803 : Common::PowerLink connect
            source ::> controller_0802.supply to sink ::> controller_0803.power;
        interface link_0803_0804 : Common::PowerLink connect
            source ::> controller_0803.supply to sink ::> controller_0804.power;
        interface link_0804_0805 : Common::PowerLink connect
            source ::> controller_0804.supply to sink ::> controller_0805.power;
        interface link_0805_0806 : Common::PowerLink connect
            source ::> controller_0805.supply to sink ::> controller_0806.power;
        interface link_0806_0807 : Common::PowerLink connect
            source ::> controller_0806.supply to sink ::> controller_0807.power;
        interface link_0807_0808 : Common::PowerLink connect
            source ::> controller_0807.supply to sink ::> controller_0808.power;
        interface link_0808_0809 : Common::PowerLink connect
            source ::> controller_0808.supply to sink ::> controller_0809.power;
        interface link_0809_0810 : Common::PowerLink connect
            source ::> controller_0809.supply to sink ::> controller_0810.power;
        interface link_0810_0811 : Common::PowerLink connect
            source ::> controller_0810.supply to sink ::> controller_0811.power;
        interface link_0811_0812 : Common::PowerLink connect
            source ::> controller_0811.supply to sink ::> controller_0812.power;
        interface link_0812_0813 : Common::PowerLink connect
            source ::> controller_0812.supply to sink ::> controller_0813.power;
        interface link_0813_0814 : Common::PowerLink connect
            source ::> controller_0813.supply to sink ::> controller_0814.power;
        interface link_0814_0815 : Common::PowerLink connect
            source ::> controller_0814.supply to sink ::> controller_0815.power;
        interface link_0815_0816 : Common::PowerLink connect
            source ::> controller_0815.supply to sink ::> controller_0816.power;
        interface link_0816_0817 : Common::PowerLink connect
            source ::> controller_0816.supply to sink ::> controller_0817.power;
        interface link_0817_0818 : Common::PowerLink connect
            source ::> controller_0817.supply to sink ::> controller_0818.power;
        interface link_0818_0819 : Common::PowerLink connect
            source ::> controller_0818.supply to sink ::> controller_0819.power;
        interface link_0819_0820 : Common::PowerLink connect
            source ::> controller_0819.supply to sink ::> controller_0820.power;
        interface link_0820_0821 : Common::PowerLink connect
            source ::> controller_0820.supply to sink ::> controller_0821.power;
        interface link_0821_0822 : Common::PowerLink connect
            source ::> controller_0821.supply to sink ::> controller_0822.power;
        interface link_0822_0823 : Common::PowerLink connect
            source ::> controller_0822.supply to sink ::> controller_0823.power;
        interface link_0823_0824 : Common::PowerLink connect
            source ::> controller_0823.supply to sink ::> controller_0824.power;
        interface link_0824_0825 : Common::PowerLink connect
            source ::> controller_0824.supply to sink ::> controller_0825.power;
        interface link_0825_0826 : Common::PowerLink connect
            source ::> controller_0825.supply to sink ::> controller_0826.power;
        interface link_0826_0827 : Common::PowerLink connect
            source ::> controller_0826.supply to sink ::> controller_0827.power;
        interface link_0827_0828 : Common::PowerLink connect
            source ::> controller_0827.supply to sink ::> controller_0828.power;
        interface link_0828_0829 : Common::PowerLink connect
            source ::> controller_0828.supply to sink ::> controller_0829.power;
        interface link_0829_0830 : Common::PowerLink connect
            source ::> controller_0829.supply to sink ::> controller_0830.power;
        interface link_0830_0831 : Common::PowerLink connect
            source ::> controller_0830.supply to sink ::> controller_0831.power;
        interface link_0831_0832 : Common::PowerLink connect
            source ::> controller_0831.supply to sink ::> controller_0832.power;
        interface link_0832_0833 : Common::PowerLink connect
            source ::> controller_0832.supply to sink ::> controller_0833.power;
        interface link_0833_0834 : Common::PowerLink connect
            source ::> controller_0833.supply to sink ::> controller_0834.power;
        interface link_0834_0835 : Common::PowerLink connect
            source ::> controller_0834.supply to sink ::> controller_0835.power;
        interface link_0835_0836 : Common::PowerLink connect
            source ::> controller_0835.supply to sink ::> controller_0836.power;
        interface link_0836_0837 : Common::PowerLink connect
            source ::> controller_0836.supply to sink ::> controller_0837.power;
        interface link_0837_0838 : Common::PowerLink connect
            source ::> controller_0837.supply to sink ::> controller_0838.power;
        interface link_0838_0839 : Common::PowerLink connect
            source ::> controller_0838.supply to sink ::> controller_0839.power;
        interface link_0839_0840 : Common::PowerLink connect
            source ::> controller_0839.supply to sink ::> controller_0840.power;
        interface link_0840_0841 : Common::PowerLink connect
            source ::> controller_0840.supply to sink ::> controller_0841.power;
        interface link_0841_0842 : Common::PowerLink connect
            source ::> controller_0841.supply to sink ::> controller_0842.power;
        interface link_0842_0843 : Common::PowerLink connect
            source ::> controller_0842.supply to sink ::> controller_0843.power;
        interface link_0843_0844 : Common::PowerLink connect
            source ::> controller_0843.supply to sink ::> controller_0844.power;
        interface link_0844_0845 : Common::PowerLink connect
            source ::> controller_0844.supply to sink ::> controller_0845.power;
        interface link_0845_0846 : Common::PowerLink connect
            source ::> controller_0845.supply to sink ::> controller_0846.power;
        interface link_0846_0847 : Common::PowerLink connect
            source ::> controller_0846.supply to sink ::> controller_0847.power;
        interface link_0847_0848 : Common::PowerLink connect
            source ::> controller_0847.supply to sink ::> controller_0848.power;
        interface link_0848_0849 : Common::PowerLink connect
            source ::> controller_0848.supply to sink ::> controller_0849.power;
        interface link_0849_0850 : Common::PowerLink connect
            source ::> controller_0849.supply to sink ::> controller_0850.power;
        interface link_0850_0851 : Common::PowerLink connect
            source ::> controller_0850.supply to sink ::> controller_0851.power;
        interface link_0851_0852 : Common::PowerLink connect
            source ::> controller_0851.supply to sink ::> controller_0852.power;
        interface link_0852_0853 : Common::PowerLink connect
            source ::> controller_0852.supply to sink ::> controller_0853.power;
        interface link_0853_0854 : Common::PowerLink connect
            source ::> controller_0853.supply to sink ::> controller_0854.power;
        interface link_0854_0855 : Common::PowerLink connect
            source ::> controller_0854.supply to sink ::> controller_0855.power;
        interface link_0855_0856 : Common::PowerLink connect
            source ::> controller_0855.supply to sink ::> controller_0856.power;
        interface link_0856_0857 : Common::PowerLink connect
            source ::> controller_0856.supply to sink ::> controller_0857.power;
        interface link_0857_0858 : Common::PowerLink connect
            source ::> controller_0857.supply to sink ::> controller_0858.power;
        interface link_0858_0859 : Common::PowerLink connect
            source ::> controller_0858.supply to sink ::> controller_0859.power;
        interface link_0859_0860 : Common::PowerLink connect
            source ::> controller_0859.supply to sink ::> controller_0860.power;
        interface link_0860_0861 : Common::PowerLink connect
            source ::> controller_0860.supply to sink ::> controller_0861.power;
        interface link_0861_0862 : Common::PowerLink connect
            source ::> controller_0861.supply to sink ::> controller_0862.power;
        interface link_0862_0863 : Common::PowerLink connect
            source ::> controller_0862.supply to sink ::> controller_0863.power;
        interface link_0863_0864 : Common::PowerLink connect
            source ::> controller_0863.supply to sink ::> controller_0864.power;
        interface link_0864_0865 : Common::PowerLink connect
            source ::> controller_0864.supply to sink ::> controller_0865.power;
        interface link_0865_0866 : Common::PowerLink connect
            source ::> controller_0865.supply to sink ::> controller_0866.power;
        interface link_0866_0867 : Common::PowerLink connect
            source ::> controller_0866.supply to sink ::> controller_0867.power;
        interface link_0867_0868 : Common::PowerLink connect
            source ::> controller_0867.supply to sink ::> controller_0868.power;
        interface link_0868_0869 : Common::PowerLink connect
            source ::> controller_0868.supply to sink ::> controller_0869.power;
        interface link_0869_0870 : Common::PowerLink connect
            source ::> controller_0869.supply to sink ::> controller_0870.power;
        interface link_0870_0871 : Common::PowerLink connect
            source ::> controller_0870.supply to sink ::> controller_0871.power;
        interface link_0871_0872 : Common::PowerLink connect
            source ::> controller_0871.supply to sink ::> controller_0872.power;
        interface link_0872_0873 : Common::PowerLink connect
            source ::> controller_0872.supply to sink ::> controller_0873.power;
        interface link_0873_0874 : Common::PowerLink connect
            source ::> controller_0873.supply to sink ::> controller_0874.power;
        interface link_0874_0875 : Common::PowerLink connect
            source ::> controller_0874.supply to sink ::> controller_0875.power;
        interface link_0875_0876 : Common::PowerLink connect
            source ::> controller_0875.supply to sink ::> controller_0876.power;
        interface link_0876_0877 : Common::PowerLink connect
            source ::> controller_0876.supply to sink ::> controller_0877.power;
        interface link_0877_0878 : Common::PowerLink connect
            source ::> controller_0877.supply to sink ::> controller_0878.power;
        interface link_0878_0879 : Common::PowerLink connect
            source ::> controller_0878.supply to sink ::> controller_0879.power;
        interface link_0879_0880 : Common::PowerLink connect
            source ::> controller_0879.supply to sink ::> controller_0880.power;
        interface link_0880_0881 : Common::PowerLink connect
            source ::> controller_0880.supply to sink ::> controller_0881.power;
        interface link_0881_0882 : Common::PowerLink connect
            source ::> controller_0881.supply to sink ::> controller_0882.power;
        interface link_0882_0883 : Common::PowerLink connect
            source ::> controller_0882.supply to sink ::> controller_0883.power;
        interface link_0883_0884 : Common::PowerLink connect
            source ::> controller_0883.supply to sink ::> controller_0884.power;
        interface link_0884_0885 : Common::PowerLink connect
            source ::> controller_0884.supply to sink ::> controller_0885.power;
        interface link_0885_0886 : Common::PowerLink connect
            source ::> controller_0885.supply to sink ::> controller_0886.power;
        interface link_0886_0887 : Common::PowerLink connect
            source ::> controller_0886.supply to sink ::> controller_0887.power;
        interface link_0887_0888 : Common::PowerLink connect
            source ::> controller_0887.supply to sink ::> controller_0888.power;
        interface link_0888_0889 : Common::PowerLink connect
            source ::> controller_0888.supply to sink ::> controller_0889.power;
        interface link_0889_0890 : Common::PowerLink connect
            source ::> controller_0889.supply to sink ::> controller_0890.power;
        interface link_0890_0891 : Common::PowerLink connect
            source ::> controller_0890.supply to sink ::> controller_0891.power;
        interface link_0891_0892 : Common::PowerLink connect
            source ::> controller_0891.supply to sink ::> controller_0892.power;
        interface link_0892_0893 : Common::PowerLink connect
            source ::> controller_0892.supply to sink ::> controller_0893.power;
        interface link_0893_0894 : Common::PowerLink connect
            source ::> controller_0893.supply to sink ::> controller_0894.power;
        interface link_0894_0895 : Common::PowerLink connect
            source ::> controller_0894.supply to sink ::> controller_0895.power;
        interface link_0895_0896 : Common::PowerLink connect
            source ::> controller_0895.supply to sink ::> controller_0896.power;
        interface link_0896_0897 : Common::PowerLink connect
            source ::> controller_0896.supply to sink ::> controller_0897.power;
        interface link_0897_0898 : Common::PowerLink connect
            source ::> controller_0897.supply to sink ::> controller_0898.power;
        interface link_0898_0899 : Common::PowerLink connect
            source ::> controller_0898.supply to sink ::> controller_0899.power;
        interface link_0899_0900 : Common::PowerLink connect
            source ::> controller_0899.supply to sink ::> controller_0900.power;
        interface link_0900_0901 : Common::PowerLink connect
            source ::> controller_0900.supply to sink ::> controller_0901.power;
        interface link_0901_0902 : Common::PowerLink connect
            source ::> controller_0901.supply to sink ::> controller_0902.power;
        interface link_0902_0903 : Common::PowerLink connect
            source ::> controller_0902.supply to sink ::> controller_0903.power;
        interface link_0903_0904 : Common::PowerLink connect
            source ::> controller_0903.supply to sink ::> controller_0904.power;
        interface link_0904_0905 : Common::PowerLink connect
            source ::> controller_0904.supply to sink ::> controller_0905.power;
        interface link_0905_0906 : Common::PowerLink connect
            source ::> controller_0905.supply to sink ::> controller_0906.power;
        interface link_0906_0907 : Common::PowerLink connect
            source ::> controller_0906.supply to sink ::> controller_0907.power;
        interface link_0907_0908 : Common::PowerLink connect
            source ::> controller_0907.supply to sink ::> controller_0908.power;
        interface link_0908_0909 : Common::PowerLink connect
            source ::> controller_0908.supply to sink ::> controller_0909.power;
        interface link_0909_0910 : Common::PowerLink connect
            source ::> controller_0909.supply to sink ::> controller_0910.power;
        interface link_0910_0911 : Common::PowerLink connect
            source ::> controller_0910.supply to sink ::> controller_0911.power;
        interface link_0911_0912 : Common::PowerLink connect
            source ::> controller_0911.supply to sink ::> controller_0912.power;
        interface link_0912_0913 : Common::PowerLink connect
            source ::> controller_0912.supply to sink ::> controller_0913.power;
        interface link_0913_0914 : Common::PowerLink connect
            source ::> controller_0913.supply to sink ::> controller_0914.power;
        interface link_0914_0915 : Common::PowerLink connect
            source ::> controller_0914.supply to sink ::> controller_0915.power;
        interface link_0915_0916 : Common::PowerLink connect
            source ::> controller_0915.supply to sink ::> controller_0916.power;
        interface link_0916_0917 : Common::PowerLink connect
            source ::> controller_0916.supply to sink ::> controller_0917.power;
        interface link_0917_0918 : Common::PowerLink connect
            source ::> controller_0917.supply to sink ::> controller_0918.power;
        interface link_0918_0919 : Common::PowerLink connect
            source ::> controller_0918.supply to sink ::> controller_0919.power;
        interface link_0919_0920 : Common::PowerLink connect
            source ::> controller_0919.supply to sink ::> controller_0920.power;
        interface link_0920_0921 : Common::PowerLink connect
            source ::> controller_0920.supply to sink ::> controller_0921.power;
        interface link_0921_0922 : Common::PowerLink connect
            source ::> controller_0921.supply to sink ::> controller_0922.power;
        interface link_0922_0923 : Common::PowerLink connect
            source ::> controller_0922.supply to sink ::> controller_0923.power;
        interface link_0923_0924 : Common::PowerLink connect
            source ::> controller_0923.supply to sink ::> controller_0924.power;
        interface link_0924_0925 : Common::PowerLink connect
            source ::> controller_0924.supply to sink ::> controller_0925.power;
        interface link_0925_0926 : Common::PowerLink connect
            source ::> controller_0925.supply to sink ::> controller_0926.power;
        interface link_0926_0927 : Common::PowerLink connect
            source ::> controller_0926.supply to sink ::> controller_0927.power;
        interface link_0927_0928 : Common::PowerLink connect
            source ::> controller_0927.supply to sink ::> controller_0928.power;
        interface link_0928_0929 : Common::PowerLink connect
            source ::> controller_0928.supply to sink ::> controller_0929.power;
        interface link_0929_0930 : Common::PowerLink connect
            source ::> controller_0929.supply to sink ::> controller_0930.power;
        interface link_0930_0931 : Common::PowerLink connect
            source ::> controller_0930.supply to sink ::> controller_0931.power;
        interface link_0931_0932 : Common::PowerLink connect
            source ::> controller_0931.supply to sink ::> controller_0932.power;
        interface link_0932_0933 : Common::PowerLink connect
            source ::> controller_0932.supply to sink ::> controller_0933.power;
        interface link_0933_0934 : Common::PowerLink connect
            source ::> controller_0933.supply to sink ::> controller_0934.power;
        interface link_0934_0935 : Common::PowerLink connect
            source ::> controller_0934.supply to sink ::> controller_0935.power;
        interface link_0935_0936 : Common::PowerLink connect
            source ::> controller_0935.supply to sink ::> controller_0936.power;
        interface link_0936_0937 : Common::PowerLink connect
            source ::> controller_0936.supply to sink ::> controller_0937.power;
        interface link_0937_0938 : Common::PowerLink connect
            source ::> controller_0937.supply to sink ::> controller_0938.power;
        interface link_0938_0939 : Common::PowerLink connect
            source ::> controller_0938.supply to sink ::> controller_0939.power;
        interface link_0939_0940 : Common::PowerLink connect
            source ::> controller_0939.supply to sink ::> controller_0940.power;
        interface link_0940_0941 : Common::PowerLink connect
            source ::> controller_0940.supply to sink ::> controller_0941.power;
        interface link_0941_0942 : Common::PowerLink connect
            source ::> controller_0941.supply to sink ::> controller_0942.power;
        interface link_0942_0943 : Common::PowerLink connect
            source ::> controller_0942.supply to sink ::> controller_0943.power;
        interface link_0943_0944 : Common::PowerLink connect
            source ::> controller_0943.supply to sink ::> controller_0944.power;
        interface link_0944_0945 : Common::PowerLink connect
            source ::> controller_0944.supply to sink ::> controller_0945.power;
        interface link_0945_0946 : Common::PowerLink connect
            source ::> controller_0945.supply to sink ::> controller_0946.power;
        interface link_0946_0947 : Common::PowerLink connect
            source ::> controller_0946.supply to sink ::> controller_0947.power;
        interface link_0947_0948 : Common::PowerLink connect
            source ::> controller_0947.supply to sink ::> controller_0948.power;
        interface link_0948_0949 : Common::PowerLink connect
            source ::> controller_0948.supply to sink ::> controller_0949.power;
        interface link_0949_0950 : Common::PowerLink connect
            source ::> controller_0949.supply to sink ::> controller_0950.power;
        interface link_0950_0951 : Common::PowerLink connect
            source ::> controller_0950.supply to sink ::> controller_0951.power;
        interface link_0951_0952 : Common::PowerLink connect
            source ::> controller_0951.supply to sink ::> controller_0952.power;
        interface link_0952_0953 : Common::PowerLink connect
            source ::> controller_0952.supply to sink ::> controller_0953.power;
        interface link_0953_0954 : Common::PowerLink connect
            source ::> controller_0953.supply to sink ::> controller_0954.power;
        interface link_0954_0955 : Common::PowerLink connect
            source ::> controller_0954.supply to sink ::> controller_0955.power;
        interface link_0955_0956 : Common::PowerLink connect
            source ::> controller_0955.supply to sink ::> controller_0956.power;
        interface link_0956_0957 : Common::PowerLink connect
            source ::> controller_0956.supply to sink ::> controller_0957.power;
        interface link_0957_0958 : Common::PowerLink connect
            source ::> controller_0957.supply to sink ::> controller_0958.power;
        interface link_0958_0959 : Common::PowerLink connect
            source ::> controller_0958.supply to sink ::> controller_0959.power;
        interface link_0959_0960 : Common::PowerLink connect
            source ::> controller_0959.supply to sink ::> controller_0960.power;
        interface link_0960_0961 : Common::PowerLink connect
            source ::> controller_0960.supply to sink ::> controller_0961.power;
        interface link_0961_0962 : Common::PowerLink connect
            source ::> controller_0961.supply to sink ::> controller_0962.power;
        interface link_0962_0963 : Common::PowerLink connect
            source ::> controller_0962.supply to sink ::> controller_0963.power;
        interface link_0963_0964 : Common::PowerLink connect
            source ::> controller_0963.supply to sink ::> controller_0964.power;
        interface link_0964_0965 : Common::PowerLink connect
            source ::> controller_0964.supply to sink ::> controller_0965.power;
        interface link_0965_0966 : Common::PowerLink connect
            source ::> controller_0965.supply to sink ::> controller_0966.power;
        interface link_0966_0967 : Common::PowerLink connect
            source ::> controller_0966.supply to sink ::> controller_0967.power;
        interface link_0967_0968 : Common::PowerLink connect
            source ::> controller_0967.supply to sink ::> controller_0968.power;
        interface link_0968_0969 : Common::PowerLink connect
            source ::> controller_0968.supply to sink ::> controller_0969.power;
        interface link_0969_0970 : Common::PowerLink connect
            source ::> controller_0969.supply to sink ::> controller_0970.power;
        interface link_0970_0971 : Common::PowerLink connect
            source ::> controller_0970.supply to sink ::> controller_0971.power;
        interface link_0971_0972 : Common::PowerLink connect
            source ::> controller_0971.supply to sink ::> controller_0972.power;
        interface link_0972_0973 : Common::PowerLink connect
            source ::> controller_0972.supply to sink ::> controller_0973.power;
        interface link_0973_0974 : Common::PowerLink connect
            source ::> controller_0973.supply to sink ::> controller_0974.power;
        interface link_0974_0975 : Common::PowerLink connect
            source ::> controller_0974.supply to sink ::> controller_0975.power;
        interface link_0975_0976 : Common::PowerLink connect
            source ::> controller_0975.supply to sink ::> controller_0976.power;
        interface link_0976_0977 : Common::PowerLink connect
            source ::> controller_0976.supply to sink ::> controller_0977.power;
        interface link_0977_0978 : Common::PowerLink connect
            source ::> controller_0977.supply to sink ::> controller_0978.power;
        interface link_0978_0979 : Common::PowerLink connect
            source ::> controller_0978.supply to sink ::> controller_0979.power;
        interface link_0979_0980 : Common::PowerLink connect
            source ::> controller_0979.supply to sink ::> controller_0980.power;
        interface link_0980_0981 : Common::PowerLink connect
            source ::> controller_0980.supply to sink ::> controller_0981.power;
        interface link_0981_0982 : Common::PowerLink connect
            source ::> controller_0981.supply to sink ::> controller_0982.power;
        interface link_0982_0983 : Common::PowerLink connect
            source ::> controller_0982.supply to sink ::> controller_0983.power;
        interface link_0983_0984 : Common::PowerLink connect
            source ::> controller_0983.supply to sink ::> controller_0984.power;
        interface link_0984_0985 : Common::PowerLink connect
            source ::> controller_0984.supply to sink ::> controller_0985.power;
        interface link_0985_0986 : Common::PowerLink connect
            source ::> controller_0985.supply to sink ::> controller_0986.power;
        interface link_0986_0987 : Common::PowerLink connect
            source ::> controller_0986.supply to sink ::> controller_0987.power;
        interface link_0987_0988 : Common::PowerLink connect
            source ::> controller_0987.supply to sink ::> controller_0988.power;
        interface link_0988_0989 : Common::PowerLink connect
            source ::> controller_0988.supply to sink ::> controller_0989.power;
        interface link_0989_0990 : Common::PowerLink connect
            source ::> controller_0989.supply to sink ::> controller_0990.power;
        interface link_0990_0991 : Common::PowerLink connect
            source ::> controller_0990.supply to sink ::> controller_0991.power;
        interface link_0991_0992 : Common::PowerLink connect
            source ::> controller_0991.supply to sink ::> controller_0992.power;
        interface link_0992_0993 : Common::PowerLink connect
            source ::> controller_0992.supply to sink ::> controller_0993.power;
        interface link_0993_0994 : Common::PowerLink connect
            source ::> controller_0993.supply to sink ::> controller_0994.power;
        interface link_0994_0995 : Common::PowerLink connect
            source ::> controller_0994.supply to sink ::> controller_0995.power;
        interface link_0995_0996 : Common::PowerLink connect
            source ::> controller_0995.supply to sink ::> controller_0996.power;
        interface link_0996_0997 : Common::PowerLink connect
            source ::> controller_0996.supply to sink ::> controller_0997.power;
        interface link_0997_0998 : Common::PowerLink connect
            source ::> controller_0997.supply to sink ::> controller_0998.power;
        interface link_0998_0999 : Common::PowerLink connect
            source ::> controller_0998.supply to sink ::> controller_0999.power;
        interface link_0999_1000 : Common::PowerLink connect
            source ::> controller_0999.supply to sink ::> controller_1000.power;
        attribute totalMass : MassValue = Common::TotalMass((controller_0001.mass, controller_0002.mass, controller_0003.mass, controller_0004.mass, controller_0005.mass, controller_0006.mass, controller_0007.mass, controller_0008.mass));
    }
    part system : System;
}
